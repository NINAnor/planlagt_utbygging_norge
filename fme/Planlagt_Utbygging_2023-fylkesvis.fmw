FME workspace Planlagt_Utbygging_2023-fylkesvis.fmw
Title: Planlagt_Utbygging_2023-fylkesvis

Parameters:
- Kommune =
- Fylke_nr = 38   # Velg fylkenummer
- Fylke = Vestfold_og_Telemark   # Velg fylke(r)
- PARAMETER_2 =   # Diverse innstillinger
- kp_exclude = 170,172,173,200,210,220,221,222,223,330,410,420,460,490,499,500,510,520,521,522,530,531,532,533,540,541,542,590,3000,3001,3002,3020,3030,3040,3050,3100,3800,4000,4001,4010,4020,4800,5000,5001,5100,5200,5210,5220,5230,6000,6001,6100,6110,6120,6130,6200,6220,6230,6300,6400,6500,6600,6700,6800   # Kommuneplan arealformål som skal ekskluderes
- arealformal_exclude = 3002,3020,3030,3040,3050,3100,3800,4001,4010,4020,4800,5100,5200,5210,5220,5230,6001,6100,6110,6120,6130,6200,6220,6230,6300,6400,6500,6600,6700,6800,9999   # Arealformål som skal ekskluderes
- OUTPUT = FME_DISCLOSURE_OPEN   # Output
- OutputSti = P:\412308_planlagt_utbygging_i_norge\planlagt-utbygging-beregning\data\output   # Velg sti for output
- DEST = ETRS89.UTM-33N   # EnableReadFromFeature:Yes Velg output-koordinatsystem
- output_csv_path = P:\412308_planlagt_utbygging_i_norge\planlagt-utbygging-beregning\data\output   # Ouput path CSV
- output_excel_kp = Plan_$(Fylke_nr)_$(Fylke)_kommuneplaner_2023   # CSV name Kommuneplaner
- output_excel_rp = Plan_$(Fylke_nr)_$(Fylke)_reguleringsplaner_2023   # CSV name Reguleringsplaner
- output_geopackage = P:\412308_planlagt_utbygging_i_norge\planlagt-utbygging-beregning\data\output\Plan_$(Fylke_nr)_$(Fylke)_25833_Planlagt-Utbygging2023.gpkg   # Planlagt Utbygging (GeoPackage)
- PARAMETER = FME_DISCLOSURE_OPEN   # Input - datakilder
- SourceDataset_SOSI_Kommuneplan = P:\412308_planlagt_utbygging_i_norge\planlagt-utbygging-beregning\data\input\kommuneplaner\kommuneplan\Plan_*$(Fylke_nr)*_*$(Fylke)*_25833_Kommuneplaner_Kommuneplan_FGDB.gdb   # Kommuneplan (FGDB)
- SourceDataset_SOSI_Kommunedelplan = P:\412308_planlagt_utbygging_i_norge\planlagt-utbygging-beregning\data\input\kommuneplaner\kommunedelplan\Plan_*$(Fylke_nr)*_*$(Fylke)*_25833_Kommuneplaner_Kommunedelplan_FGDB.gdb   # Kommunedelplaner (FGDB)
- SourceDataset_FILEGDB_13 = P:\412308_planlagt_utbygging_i_norge\planlagt-utbygging-beregning\data\input\reguleringsplaner\reguleringsplan\Plan_*$(Fylke_nr)*_*$(Fylke)*_25833_Reguleringsplaner_vn2_FGDB.gdb   # Reguleringsplaner (FGDB)
- SourceDataset_FILEGDB_15 = R:\GeoSpatialData\Topography\Norway_FKB\Original\FKB-AR5 FGDB-format\Basisdata_*$(Fylke_nr)*_*$(Fylke)*_25832_FKB-AR5_FGDB.gdb   # FKB AR5 (FGDB)
- SSBArealbruk = P:\15227000_kartlegging_av_tomtereserve_for_fritidsbebyggels\willeke\ssb-arealbruk-2022\Befolkning_*$(Fylke_nr)*_*$(Fylke)*_25833_Arealbruk2022_FGDB\Befolkning_*$(Fylke_nr)*_*$(Fylke)*_25833_Arealbruk2022_FGDB.gdb   # SSB Arealbruk (FGDB)
- SourceDataset_FILEGDB_10 = R:\GeoSpatialData\Topography\Norway_FKB\Original\FKB-Veg FGDB-format\Basisdata_*$(Fylke_nr)*_*$(Fylke)*_5972_FKB-Veg_FGDB.gdb   # FKB Veg - flate (FGDB)
- SourceDataset_FILEGDB = R:\GeoSpatialData\Topography\Norway_FKB\Original\FKB-Bygning FGDB-format\Basisdata_*$(Fylke_nr)*_*$(Fylke)*_5972_FKB-Bygning_FGDB.gdb   # FKB Bygning - flate (FGDB)
- SourceDataset_FILEGDB_17 = P:\412308_planlagt_utbygging_i_norge\planlagt-utbygging-beregning\data\input\fkb-tiltak\Basisdata_0000_Norge_5973_FKB-Tiltak_FGDB.gdb   # FKB Tiltak (FGDB)
- SourceDataset_XLSXR_5 = P:\412308_planlagt_utbygging_i_norge\planlagt-utbygging-beregning\data\input\Reguleringsplaner_Ikke_Med.xlsx   # Ekskluderte reguleringsplaner (Excel)

Readers:
- GEODATABASE_FILE_2: GEODATABASE_FILE from $(SSBArealbruk)
- XLSXR_2: XLSXR from $(SourceDataset_XLSXR_5)
- FILEGDB_2: FILEGDB from $(SourceDataset_SOSI_Kommuneplan)
- FILEGDB_6: FILEGDB from $(SourceDataset_SOSI_Kommunedelplan)
- FILEGDB_7: FILEGDB from $(SourceDataset_FILEGDB)
- FILEGDB_1: FILEGDB from $(SourceDataset_FILEGDB_10)
- FILEGDB_5: FILEGDB from $(SourceDataset_FILEGDB_17)
- FILEGDB_3: FILEGDB from $(SourceDataset_FILEGDB_13)
- FILEGDB_4: FILEGDB from $(SourceDataset_FILEGDB_15)

Writers:
- CSV2_1: CSV2 to $(output_csv_path)

Junction_4
    -> Planlagt_utbygd_areal_beregning [Ekskluderingsflate]
Junction_9
    -> Planlagt_utbygd_areal_beregning [Fkb_tiltak]
Junction_12
    -> Planlagt_utbygd_areal_beregning [Fkb_veg]
Junction_15
    -> Planlagt_utbygd_areal_beregning [Fkb_bygning]
Junction_6
    -> Planlagt_utbygd_areal_beregning [SSB_Arealbruk]
Junction_18
    -> Planlagt_utbygd_areal_beregning [AR5]
Note: *$Kommune* og *$Fylke* er dynamiske tree variabeler, som kan brukes til å filtrere på en elller flere kommuner/fylker og kjøre workspacen fylkesvis. / Hvis du klikker på "Run entire workspace" eller "Run from this" kan du velge fylke/kommune.
Note: NB: Leserne har 'Individual Feature Types' og dersom inputen har andre navn på objekttype/feature type/feature class, så kommer de ikke med. Oppdater i så fall 'Feature Types' i toppmenyen under Readers.
Junction_8
    -> Clipper_3 [CLIPPER]
    -> AttributeKeeper_10
Note: Legg til: / - Arealformålsgruppe / - Arealformål / --> LookUp table: / Legg til Admin: / - DateTime / - fylkesnavn og fylkenr / - kommunenavn og kommunenr / --> lookup tabel / Overlapp av planer: / Concat: 2 .. rp og 2 kp gamle planner ligger under.
Junction_2
    -> Planlagt_utbygd_areal_beregning [PLAN]
Planlagt_utbygd_areal_beregning
    AREALFORMAL = @Value(arealformal)
    AREALFORMALKODE = @Value(arealformalkode)
    AREALFORMALSGRUPPE_2 = @Value(arealformalsgruppe)
    AREALSTATUS = @Value(arealstatus)
    AREALTYPE = @Value(arealtype)
    FYLKE = @Value(fylke)
    FYLKESNUMMER = @Value(fylkesnummer)
    HOVEDKLASSE = @Value(hovedklasse)
    IKRAFTTREDELSESDATO = @Value(ikrafttredelsesdato)
    KOMMUNE = @Value(kommune)
    KOMMUNENUMMER = @Value(kommunenummer)
    KP_FORMAL = @Value(kp_formal)
    Kommune = $(Kommune)
    LOVREFERANSE = @Value(lovreferanse)
    OMRADENAVN = @Value(omradenavn)
    OutputSti = $(OutputSti)
    PLANBESTEMMELSE = @Value(planbestemmelse)
    PLANID = @Value(planid)
    PLANKILDE = @Value(plankilde)
    PLANLAGT_AREAL_M2 = @Value(planlagt_areal_m2)
    PLANNAVN = @Value(plannavn)
    PLANNMOSAIKKDATO = @Value(plannmosaikkdato)
    PLANSTATUS = @Value(planstatus)
    PLANTYPE = @Value(plantype)
    PLAN_OVERLAPP = @Value(plan_overlapp)
    RP_FORMAL = @Value(rp_formal)
    arealformal_exclude = 3002,3020,3030,3040,3050,3100,3800,4001,4010,4020,4800,5100,5200,5210,5220,5230,6001,6100,6110,6120,6130,6200,6220,6230,6300,6400,6500,6600,6700,6800,9999
    rp_exclude = 200,210,220,230,299,392,400,410,420,421,430,450,459,460,461,463,469,540,550,590,600,611,613,614,619,622,626,631,645,646,650,651,652,660,661,662,663,680,681,699,780,999,1587,1588,3000,3001,3002,3020,3030,3031,3040,3041,3050,3060,3061,3100,3110,3800,3900,4000,4001,4010,4020,4800,4900,5000,5001,5100,5110,5111,5112,5113,5114,5115,5120,5130,5140,5200,5210,5220,5230,5300,5400,5500,5600,5900,6000,6001,6100,6110,6120,6130,6200,6210,6211,6220,6230,6240,6300,6310,6320,6330,6400,6410,6500,6600,6610,6620,6700,6710,6720,6730,6740,6760,6770,6800,6900
    -> AttributeManager_3
AttributeManager_3
    ATTR_TABLE = REMOVE hovedklasse
    USER_EXPOSED_ATTRIBUTES = planlagt_utbygging
    -> AttributeValueMapper_8
AttributeValueMapper_8
    LUT = 0,Nei,1,Ja,9999,Arealformål ekskludert fra beregning
    MAPPING_DIRECTION = FORWARD
    SRC = pu_code
    VAL_ATTR = planlagt_utbygging
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(pu_code) = 1",Planlagt Utbygging,"BOOL_OP,OR,COMPOSITE_TEST,""""""1"""""",TEST_CLAUSE,TEST @Value(pu_code) = 0",Bebygd og Restareal,"BOOL_OP,OR,COMPOSITE_TEST,""""""1"""""",TEST_CLAUSE,TEST @Value(pu_code) = 9999",ekskludert fra beregning
    Planlagt Utbygging -> Aggregator_2
    Bebygd og Restareal -> Aggregator_4
    ekskludert fra beregning -> Aggregator_3
Junction_48
    -> TestFilter_3
    -> AttributeManager_8

Bookmark: Flate for å ekskludere et område i planreserveberegningen (Erstatt Creator med med en egen reader)
Creator [off]
    GEOMTYPE = Geometry Object
    NUM = 1
    CREATED -> CsmapReprojector_10
CsmapReprojector_10 [off]
    DEST = $(DEST)
    INTERPOLATION_TYPE_NAME = Nearest Neighbor
    RASTER_CELL_SIZE = Preserve Cells
    RASTER_TOLERANCE = 0.0
    REPROJECTED -> Junction_3
Note: Planlagt_utbygd_areal_beregning : Ekskluderingsflate
Junction_3 [off]
    -> Junction_4

Bookmark: FKB Veg og FKB Bygning til planreserveberegning
fkb_tiltak_omrade (reader FILEGDB_5)
    attributes: OBJECTID objectid, objtype text(100), lokalid text(100), datafangstdato date, oppdateringsdato date, informasjon text(255), sluttdato date, navnerom text(100), versjonid text(100), datafangstmetode text(3), noyaktighet int, synbarhet text(1), datafangstmetodehoyde text(3), noyaktighethoyde int, eksternpeker text(255), medium text(1), saksreferanse text(50), behandlingsstatus text(10), kartregistrering int, behandlingsdato date, tiltaksansvarlig text(25), andretiltak text(25), bygningsnummer int, bygningsendringlopenummer int, hoydereferanse text(6), lavestegulv double, hoydeoverbakken double, tiltakstypebygning text(30), SHAPE_Length double, SHAPE_Area double
    -> CsmapReprojector_13
CsmapReprojector_13
    DEST = $(DEST)
    INTERPOLATION_TYPE_NAME = Nearest Neighbor
    RASTER_CELL_SIZE = Preserve Cells
    RASTER_TOLERANCE = 0.0
    REPROJECTED -> AttributeKeeper_15
AttributeKeeper_15
    CREATE_BULK_MODE_FEATURES = NO
    -> Junction_7
Note: Planlagt_utbygd_areal_beregning : Fkb_tiltak
Junction_7
    -> Junction_9
fkb_veg_omrade (reader FILEGDB_1)
    attributes: OBJECTID objectid, objtype text(32), lokalid text(100), navnerom text(100), versjonid text(100), datafangstdato date, informasjon text(255), kopidato date, omradeid int, originaldatavert text(100), medium text(1), oppdateringsdato date, prosesshistorie text(255), produkt text(15), versjon text(50), undertype text(20), vegoverveg smallint, verifiseringsdato date, vegkategori text(1), vegnummer int, vegstatus text(1), SHAPE_Length double, SHAPE_Area double
    -> CsmapReprojector_9
CsmapReprojector_9
    DEST = $(DEST)
    INTERPOLATION_TYPE_NAME = Nearest Neighbor
    RASTER_CELL_SIZE = Preserve Cells
    RASTER_TOLERANCE = 0.0
    REPROJECTED -> AttributeKeeper_12
AttributeKeeper_12
    CREATE_BULK_MODE_FEATURES = NO
    -> Junction_11
Note: Planlagt_utbygd_areal_beregning : Fkb_veg
Junction_11
    -> Junction_12
fkb_bygning_omrade (reader FILEGDB_7)
    attributes: OBJECTID objectid, objtype text(32), bygningsnummer int, datafangstdato date, lokalid text(100), navnerom text(100), versjonid text(100), produkt text(15), versjon text(50), undertype text(20), verifiseringsdato date, oppdateringsdato date, informasjon text(255), prosesshistorie text(255), omradeid int, originaldatavert text(100), kopidato date, bygningstype int, bygningsstatus text(255), kommunenummer text(4), innmalingsstatus text(255), medium text(1), SHAPE_Length double, SHAPE_Area double
    -> CsmapReprojector_7
CsmapReprojector_7
    DEST = $(DEST)
    INTERPOLATION_TYPE_NAME = Nearest Neighbor
    RASTER_CELL_SIZE = Preserve Cells
    RASTER_TOLERANCE = 0.0
    REPROJECTED -> AttributeKeeper_5
AttributeKeeper_5
    CREATE_BULK_MODE_FEATURES = NO
    -> Junction_13
Junction_13
    -> Junction_15

Bookmark: SSB Arealbruk
ssbarealbrukflate (reader GEODATABASE_FILE_2)
    attributes: OBJECTID integer, objtype char(32), lokalid char(100), navnerom char(100), versjonid char(100), noyaktighet integer, maksimaltavvik integer, datauttaksdato date, opphav char(255), kilde char(18), hovedklasse char(18), underklasse char(18), malemetode integer, synbarhet integer, SHAPE_Length double, SHAPE_Area double
    -> CsmapReprojector_5
CsmapReprojector_5
    DEST = $(DEST)
    INTERPOLATION_TYPE_NAME = Nearest Neighbor
    RASTER_CELL_SIZE = Preserve Cells
    RASTER_TOLERANCE = 0.0
    REPROJECTED -> AttributeKeeper_6
AttributeKeeper_6
    CREATE_BULK_MODE_FEATURES = NO
    KEEP_ATTRS = hovedklasse,underklasse
    -> Junction_5
Junction_5
    -> Junction_6

Bookmark: Arealressurs AR5 (FGDB)
fkb_ar5_omrade (reader FILEGDB_4)
    attributes: OBJECTID objectid, objtype text(100), lokalid text(100), datafangstdato date, verifiseringsdato date, oppdateringsdato date, informasjon text(255), sluttdato date, registreringsversjon text(10), navnerom text(100), versjonid text(100), opphav text(5), arealtype text(2), treslag text(2), skogbonitet text(2), grunnforhold text(2), klassifiseringsmetode text(10), SHAPE_Length double, SHAPE_Area double
    -> CsmapReprojector_6
CsmapReprojector_6
    DEST = $(DEST)
    INTERPOLATION_TYPE_NAME = Nearest Neighbor
    RASTER_CELL_SIZE = Preserve Cells
    RASTER_TOLERANCE = 0.0
    REPROJECTED -> AttributeKeeper_13
AttributeKeeper_13
    CREATE_BULK_MODE_FEATURES = NO
    KEEP_ATTRS = arealtype
    -> Junction_16
Junction_16
    -> Junction_18

Bookmark: Pre PBL2008
kparealbrukomrade (reader FILEGDB_2)
    attributes: OBJECTID objectid, objtype text(32), arealbruksutdyping text(100), omradenavn text(20), utnyttingstall double, utnyttingstall_minimum double, uteoppholdsareal int, planidentifikasjon text(16), lokalid text(100), navnerom text(100), versjonid text(100), omradeid int, originaldatavert text(100), kopidato date, forstedigitaliseringsdato date, oppdateringsdato date, arealbruk int, arealbruksstatus int, utnyttingstype int, kommunenummer text(4), SHAPE_Length double, SHAPE_Area double
    -> CsmapReprojector_3

Bookmark: Post PBL2008
kparealformalomrade (reader FILEGDB_2)
    attributes: OBJECTID objectid, objtype text(32), beskrivelse text(100), omradenavn text(20), uteoppholdsareal int, planidentifikasjon text(16), lokalid text(100), navnerom text(100), versjonid text(100), omradeid int, originaldatavert text(100), kopidato date, forstedigitaliseringsdato date, oppdateringsdato date, arealformal int, arealbruksstatus int, eierform int, kommunenummer text(4), SHAPE_Length double, SHAPE_Area double
    -> CsmapReprojector_3

Bookmark: Kommuneplan
CsmapReprojector_3
    DEST = $(DEST)
    INTERPOLATION_TYPE_NAME = Nearest Neighbor
    RASTER_CELL_SIZE = Preserve Cells
    RASTER_TOLERANCE = 0.0
    REPROJECTED -> Tester_12 [off]
    REPROJECTED -> Clipper_3 [CANDIDATE]
Tester_12 [off]
    BOOL_OP = OR
    TEST_CLAUSE = TEST @Value(kommunenummer) = $(Kommune)
    TEST_MODE = TEST
AttributeKeeper_4
    CREATE_BULK_MODE_FEATURES = NO
    KEEP_ATTRS = ikrafttredelsesdato,planidentifikasjon,kommunenummer,lovreferanse,planbestemmelse,plannavn,planstatus,plantype
    -> Junction
Junction
    -> Junction_17

Bookmark: Fellesegenskaper Planområde
kpomrade (reader FILEGDB_2)
    attributes: OBJECTID objectid, objtype text(32), planidentifikasjon text(16), lovreferansebeskrivelse text(120), ikrafttredelsesdato date, plannavn text(120), vedtakendeligplandato date, kunngjoringsdato date, opprinneligplanid text(16), opprinneligadministrativenhet text(4), lokalid text(100), navnerom text(100), versjonid text(100), omradeid int, originaldatavert text(100), kopidato date, forstedigitaliseringsdato date, oppdateringsdato date, kommunenummer text(4), plantype int, planstatus int, planbestemmelse int, lovreferanse int, prosesshistorie text(255), informasjon text(255), link text(255), SHAPE_Length double, SHAPE_Area double
    -> CsmapReprojector_11
CsmapReprojector_11
    DEST = $(DEST)
    INTERPOLATION_TYPE_NAME = Nearest Neighbor
    RASTER_CELL_SIZE = Preserve Cells
    RASTER_TOLERANCE = 0.0
    REPROJECTED -> Tester_7 [off]
    REPROJECTED -> AttributeKeeper_4
Tester_7 [off]
    BOOL_OP = OR
    TEST_CLAUSE = TEST @Value(kommunenummer) = $(Kommune)
    TEST_MODE = TEST
    PASSED -> Kommune_Inspector_6 [off]
Kommune_Inspector_6: Inspector [off]

Bookmark: Fellesegenskaper Planområde
kpomrade (reader FILEGDB_6)
    attributes: OBJECTID objectid, objtype text(32), planidentifikasjon text(16), lovreferansebeskrivelse text(120), ikrafttredelsesdato date, plannavn text(120), vedtakendeligplandato date, kunngjoringsdato date, opprinneligplanid text(16), opprinneligadministrativenhet text(4), lokalid text(100), navnerom text(100), versjonid text(100), omradeid int, originaldatavert text(100), kopidato date, forstedigitaliseringsdato date, oppdateringsdato date, kommunenummer text(4), plantype int, planstatus int, planbestemmelse int, lovreferanse int, prosesshistorie text(255), informasjon text(255), link text(255), SHAPE_Length double, SHAPE_Area double
    -> CsmapReprojector_8
CsmapReprojector_8
    DEST = $(DEST)
    INTERPOLATION_TYPE_NAME = Nearest Neighbor
    RASTER_CELL_SIZE = Preserve Cells
    RASTER_TOLERANCE = 0.0
    REPROJECTED -> Tester_2 [off]
    REPROJECTED -> AttributeKeeper_4
Tester_2 [off]
    BOOL_OP = OR
    TEST_CLAUSE = TEST @Value(kommunenummer) = $(Kommune)
    TEST_MODE = TEST
    PASSED -> Kommune_Inspector_5 [off]
Kommune_Inspector_5: Inspector [off]

Bookmark: Fjerner overlappende kommuneplan (behold nyeste plan)
Note: Junction_14 : Output
Junction_17
    -> FeatureMerger_5 [SUPPLIER]
Note: Slå sammen fellesegenskaper med rp post og pre pbl. 2008 basert på planid og kommunenr.
FeatureMerger_5
    ATTR_ACCUM_MODE = Merge Supplier
    ATTR_CONFLICT_RES = Use Requestor
    IGNORE_NULLS = No
    JOIN_KEYS = @Value(planid) @Value(planidentifikasjon) AUTO @Value(kommunenummer) @Value(kommunenummer) AUTO
    MERGE_TYPE = Attributes Only
    PROCESS_DUPS = NO
    REJECT_NULL_MISSING_KEYS = No
    SUPPLIERS_FIRST = No
    MERGED -> Clipper_2 [CANDIDATE]
    MERGED -> AreaOnAreaOverlayer_3 [AREA]
    UNMERGED_REQUESTOR -> Clipper_2 [CANDIDATE]
Note: Beregn antall overlappende planer
AreaOnAreaOverlayer_3
    ACCUM_ATTRS_NAME = Merge Incoming Attributes
    CLEANING_TOLERANCE = Automatic
    CONNECT_Z_MODE = First Wins
    DEAGGREGATE_INPUT = Yes
    LIST_ATTRS_TO_INCLUDE = ikrafttredelsesdato kommunenummer planidentifikasjon lovreferanse planbestemmelse planid plankilde plannavn planstatus plantype arealstatus kp_formal omradenavn arealformalkode
    LIST_NAME = attri
    OVC_ATTR = _overlaps
    AREA -> UUIDGenerator_3
UUIDGenerator_3
    UUID_ATTR = _uuid
    UUID_FORMAT = UUID_ONLY
    -> ListExploder_2
ListExploder_2
    ATTR_ACCUM_MODE = Prefix List Attributes
    INCOMING_PREFIX = _attri_
    INDEX_ATTR = _element_index
    LIST_ATTR = attri{}
    ELEMENTS -> Tester_8
Note: Test planoverlapp: / 1 = no overlapp / > 1 = overlapp (pass)
Tester_8
    BOOL_OP = OR
    TEST_CLAUSE = TEST @Value(_overlaps) > 1
    TEST_MODE = TEST
    PASSED -> BulkAttributeRemover_2
BulkAttributeRemover_2
    ATTR_EXP = \b[^_]\w+
    -> Sorter_2
Note: sorter etter ikraftredelsedato (descending)
Sorter_2
    SORT_PARM = _attri_ikrafttredelsesdato NUMERIC DESCENDING
    SORTED -> Sampler_2
Note: behold nyeste plan
Sampler_2
    GROUP_BY = _uuid
    RATE = 1
    SAMPLE_MODE = No
    SAMPLE_TYPE_LONG = First N Features
    SAMPLED -> AttributeRemover_3
AttributeRemover_3
    REMOVE_ATTRS = _element_index,_attri_planidentifikasjon,_uuid
    -> BulkAttributeRenamer_2
BulkAttributeRenamer_2
    ATTRCHOICE = All Attributes
    CASE_DISP = YES
    MODE_CHOICE = RENAME
    PATTERN_ACTION_DISP = REMOVEPREFIX
    REPLACE_STR = _attri_
    -> Dissolver_2
Dissolver_2
    ACCUM_INPUT_ATTRS = Use Attributes From One Feature
    CLEANING_TOLERANCE = Automatic
    CONNECT_Z_MODE = First Wins
    DEAGGREGATE_INPUT = Yes
    GROUP_BY = ikrafttredelsesdato kommunenummer planid plankilde _overlaps arealstatus fme_feature_type kp_formal lovreferanse omradenavn planbestemmelse plannavn planstatus plantype arealformalkode
    AREA -> Clipper_2 [CLIPPER]
    AREA -> Junction_14
Note: Klipp bort planområder som overlapper.
Clipper_2
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Junction_14
Note: Legg till den nyeste plan av de overlappende planer.
Junction_14
    -> AttributeKeeper_7
AttributeKeeper_7
    CREATE_BULK_MODE_FEATURES = NO
    KEEP_ATTRS = ikrafttredelsesdato,kommunenummer,lovreferanse,planbestemmelse,planid,plankilde,plannavn,planstatus,plantype,_overlaps,arealstatus,kp_formal,omradenavn,arealformalkode
    -> NullAttributeMapper_2
NullAttributeMapper_2
    ATTRCHOICE = Selected Attributes
    ATTRLIST = _overlaps
    NEW_VALUE = 1
    NULL_TREATMENT = New Value
    SOURCE_ATTR_VAL = Null Empty "Missing (Selected Attributes Only)"
    -> AttributeManager_2

Bookmark: Pre PBL2008
kparealbrukomrade (reader FILEGDB_6)
    attributes: OBJECTID objectid, objtype text(32), arealbruksutdyping text(100), omradenavn text(20), utnyttingstall double, utnyttingstall_minimum double, uteoppholdsareal int, planidentifikasjon text(16), lokalid text(100), navnerom text(100), versjonid text(100), omradeid int, originaldatavert text(100), kopidato date, forstedigitaliseringsdato date, oppdateringsdato date, arealbruk int, arealbruksstatus int, utnyttingstype int, kommunenummer text(4), SHAPE_Length double, SHAPE_Area double
    -> CsmapReprojector_4

Bookmark: Post PBL2008
kparealformalomrade (reader FILEGDB_6)
    attributes: OBJECTID objectid, objtype text(32), beskrivelse text(100), omradenavn text(20), uteoppholdsareal int, planidentifikasjon text(16), lokalid text(100), navnerom text(100), versjonid text(100), omradeid int, originaldatavert text(100), kopidato date, forstedigitaliseringsdato date, oppdateringsdato date, arealformal int, arealbruksstatus int, eierform int, kommunenummer text(4), SHAPE_Length double, SHAPE_Area double
    -> CsmapReprojector_4

Bookmark: Kommunedelplan
CsmapReprojector_4
    DEST = $(DEST)
    INTERPOLATION_TYPE_NAME = Nearest Neighbor
    RASTER_CELL_SIZE = Preserve Cells
    RASTER_TOLERANCE = 0.0
    REPROJECTED -> Tester_4 [off]
    REPROJECTED -> Junction_8
Tester_4 [off]
    BOOL_OP = OR
    TEST_CLAUSE = TEST @Value(kommunenummer) = $(Kommune)
    TEST_MODE = TEST
    PASSED -> Kommune_Inspector_4 [off]
Kommune_Inspector_4: Inspector [off]

Bookmark: Kommuneplan - Klargjøring før koblign med øvrige plandata
Clipper_3
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeKeeper_10
AttributeKeeper_10
    CREATE_BULK_MODE_FEATURES = NO
    KEEP_ATTRS = arealbruksstatus,arealformal,objtype,omradenavn,kommunenummer,planidentifikasjon,arealbruk
    -> Tester_11
Tester_11
    BOOL_OP = OR
    TEST_CLAUSE = CASE_INSENSITIVE_TEST @Value(objtype) BEGINS_WITH KpArealbruk
    TEST_MODE = CASE_INSENSITIVE_TEST
    PASSED -> AttributeRenamer_8
    FAILED -> AttributeRenamer_11
Note: KpArealbrukOmrade
AttributeRenamer_8
    ATTR_TABLE = RENAME_SET_DEFAULT arealbruk > kp_formal = FME_NULL_VALUE
    MISSING_INPUT_ATTRS = SET
    -> AttributeRenamer_6
Note: KpArealformalOmrade
AttributeRenamer_11
    ATTR_TABLE = RENAME_SET_DEFAULT arealformal > kp_formal = FME_NULL_VALUE
    MISSING_INPUT_ATTRS = SET
    -> AttributeRenamer_6
AttributeRenamer_6
    ATTR_TABLE:
      RENAME_SET_DEFAULT planidentifikasjon > planid
      RENAME_SET_DEFAULT objtype > plankilde
    MISSING_INPUT_ATTRS = REMOVE
    -> AttributeCreator_3
Note: Arealbrukstatus framtidg (2) --> 2 / null/nåværende (1)/videreutvikling av nåverende (3) --> 2
AttributeCreator_3
    ATTR_TABLE = SET_TO arealstatus = FME_CONDITIONAL:DEFAULT_VALUE'1'BOOL_OP;OR;COMPOSITE_TEST;1;TEST @Value(arealbruksstatus) = 2'2'FME_NUM_CONDITIONS2___
    -> AttributeKeeper_9
AttributeKeeper_9
    CREATE_BULK_MODE_FEATURES = NO
    KEEP_ATTRS = kp_formal,omradenavn,plankilde,arealstatus,kommunenummer,planid
    -> AttributeValueMapper_6

Bookmark: Kommuneplan - Verdi oversettelse av Arealformål
Note: Kommuneplan - Klargjøring før kobling med øvrige plandata / Oversetting av arealbruk og arealformal til Arealformål verdier med bruk av kommuneplankobling: / kp_formal --> arealformalkode
AttributeValueMapper_6
    LUT = 100,1001,1000,1001,1001,1001,101,1110,102,1110,110,1110,1110,1110,1120,1120,1130,1130,1140,1140,1150,1150,1160,1160,1170,1170,120,1130,1200,1200,130,1300,1300,1300,131,1150,132,1300,133,1300,134,1300,140,1120,1400,1400,150,1160,1500,1500,155,1160,160,1160,1600,1600,161,1700,162,1160,163,1160,170,3040,1700,1700,171,1400,172,3050,173,3030,1800,1800,190,1500,191,1500,200,5100,2000,2001,2001,2001,2010,2010,2020,2020,2030,2030,2040,2040,2044,2044,2050,2050,2060,2060,2070,2070,2080,2080,210,5100,2100,2100,220,5200,221,5210,222,5230,223,5220,2800,2800,300,1200,3000,3002,3001,3002,3002,3002,3020,3020,3030,3030,3040,3040,3050,3050,310,1200,3100,3100,320,1200,330,5100,3800,3800,400,1001,4000,4001,4001,4001,4010,4010,4020,4020,4030,4030,410,5100,420,5100,460,4001,470,1500,4800,4800,490,5100,499,5100,500,6001,5000,5100,5001,5100,510,6500,5100,5100,520,6700,5200,5220,521,6230,5210,5210,522,6700,5220,5220,5230,5230,530,6001,531,6100,532,6300,533,6400,540,6001,541,6700,542,6600,590,6800,600,2001,6000,6001,6001,6001,610,2010,6100,6100,6110,6110,6120,6120,6130,6130,620,2080,6200,6200,6220,6220,6230,6230,630,2001,6300,6300,631,2001,632,2050,640,2070,6400,6400,641,2070,650,2020,6500,6500,660,2020,6600,6600,670,2030,6700,6700,680,2040,6800,6800
    MAPPING_DIRECTION = FORWARD
    SRC = kp_formal
    VAL_ATTR = arealformalkode
    -> Tester_6
Note: Beholde planer med byggeformål. Se kp_exclude liste.
Tester_6
    BOOL_OP = OR
    TEST_CLAUSE = TEST @Value(kp_formal) IN $(kp_exclude)
    TEST_MODE = TEST
    FAILED -> FeatureMerger_5 [REQUESTOR]

Bookmark: CSV Renset Kommuneplaner
AttributeManager_2
    ATTR_TABLE = RENAME_SET_VALUE _overlaps > kp_overlapp
    -> Kommuneplanmosaikk
    -> renset_kommuneplaner_2023 (writer CSV2_1)
    -> AttributeRenamer_7
renset_kommuneplaner_2023 (writer CSV2_1)
    attributes: plankilde varchar(32), planid varchar(16), kp_formal string, arealformalkode string, omradenavn varchar(20), arealstatus varchar(200), plannavn varchar(120), plantype string, planstatus string, planbestemmelse string, lovreferanse string, ikrafttredelsesdato datetime, kp_overlapp uint32, kommunenummer varchar(4)
Kommuneplanmosaikk: Inspector

Bookmark: UNION mellom Kommuneplan og Reguleringsplan
AttributeRenamer_7
    ATTR_TABLE:
      RENAME_SET_DEFAULT arealformalkode > Kpl_arealformalkode
      RENAME_SET_DEFAULT plankilde > Kpl_plankilde
    MISSING_INPUT_ATTRS = REMOVE
    -> AreaOnAreaOverlayer_2 [AREA]
AreaOnAreaOverlayer_2
    ACCUM_ATTRS_NAME = Merge Incoming Attributes
    CLEANING_TOLERANCE = Automatic
    CONNECT_Z_MODE = First Wins
    DEAGGREGATE_INPUT = Yes
    AREA -> Tester_5
Tester_5
    BOOL_OP = OR
    TEST_CLAUSE = NUM_TEST arealformalkode ATTRIBUTE_IS_MISSING ""
    TEST_MODE = NUM_TEST
    PASSED -> BulkAttributeRenamer_3
    FAILED -> AttributeCreator_9
Note: Set reguleringsplaner til arealbrukstatus = 1 (nåvaerend)
AttributeCreator_9
    ATTR_TABLE = SET_TO arealstatus = FME_CONDITIONAL:DEFAULT_VALUE'_FME_NO_OP_'BOOL_OP;OR;COMPOSITE_TEST;1;TEST Arealstatus ATTRIBUTE_IS_MISSING _FME_BLANK_STRING_'1'FME_NUM_CONDITIONS2___
    -> Tester_9
Note: Kommuneplaner med arealstatus=2 har forrang foran eldre regplaner (pre pbl 2008)
Tester_9
    BOOL_OP = COMPOSITE
    COMPOSITE_TEST = 1 AND 2
    TEST_CLAUSE:
      TEST @Value(plankilde) = RbFormålOmråde
      TEST @Value(arealstatus) = 2
    TEST_MODE = TEST
    PASSED -> AttributeKeeper_11
    FAILED -> AttributeKeeper
AttributeKeeper_11
    CREATE_BULK_MODE_FEATURES = NO
    KEEP_ATTRS = KplPlankilde,Arealstatus,Områdenavn,Planid,KpFormål,RpFormål,KplArealformålkode,arealformalkode,arealstatus,ikrafttredelsesdato,kommunenummer,kp_formal,kp_overlapp,Kpl_arealformalkode,Kpl_plankilde,lovreferanse,omradenavn,planbestemmelse,planid,plankilde,plannavn,planstatus,plantype,rp_formal,rp_overlapp
    -> BulkAttributeRenamer_3
Note: Kpl old
BulkAttributeRenamer_3
    ATTRCHOICE = All Attributes
    CASE_DISP = YES
    MODE_CHOICE = RENAME
    PATTERN_ACTION_DISP = REMOVEPREFIX
    REPLACE_STR = Kpl_
    -> Junction_10
AttributeKeeper
    CREATE_BULK_MODE_FEATURES = NO
    KEEP_ATTRS = arealformalkode,arealstatus,ikrafttredelsesdato,kommunenummer,kp_formal,kp_overlapp,lovreferanse,omradenavn,planbestemmelse,planid,plankilde,plannavn,planstatus,plantype,rp_formal,rp_overlapp
    -> Junction_10
Junction_10
    -> AttributeValueMapper_7

Bookmark: Opsjonelt excelark for ekskludering av reguleringsplaner
Note: Opsjonelt excelark med kommunenummer og planidentifikasjon som skal ekskluderes
Ark1 (reader XLSXR_2) [off]
    attributes: Kommune number(5,0), Planid char(12)
    -> Tester_17
Tester_17
    BOOL_OP = OR
    TEST_CLAUSE = TEST @Value(Kommune) = $(Kommune)
    TEST_MODE = TEST
    PASSED -> FeatureMerger_3 [SUPPLIER] [off]

Bookmark: RbFormalOmrade: Reguleringsplan pbl. 1985 eller før (Pre PBL2008)
RbFormalOmrade (reader FILEGDB_3)
    attributes: OBJECTID objectid, objtype text(32), kommunenummer text(4), planidentifikasjon text(16), reguleringsformal int, reguleringsformalsutdyping text(100), vertikalniva smallint, feltbetegnelse text(20), utnyttingstype int, utnyttingstall double, utnyttingstall_minimum double, uteoppholdsareal int, byggverkbestemmelse smallint, avkjorselsbestemmelse smallint, forstedigitaliseringsdato date, oppdateringsdato date, omradeid int, originaldatavert text(100), kopidato date, lokalid text(100), navnerom text(100), versjonid text(100), SHAPE_Length double, SHAPE_Area double
    -> CsmapReprojector
CsmapReprojector
    DEST = $(DEST)
    INTERPOLATION_TYPE_NAME = Nearest Neighbor
    RASTER_CELL_SIZE = Preserve Cells
    RASTER_TOLERANCE = 0.0
    REPROJECTED -> Tester [off]
    REPROJECTED -> AttributeKeeper_3
AttributeKeeper_3
    CREATE_BULK_MODE_FEATURES = NO
    KEEP_ATTRS = reguleringsformal,objtype,planidentifikasjon,kommunenummer
    -> AttributeRenamer_3
Tester [off]
    BOOL_OP = OR
    TEST_CLAUSE = NUM_TEST @Value(kommunenummer) IN $(Kommune)
    TEST_MODE = NUM_TEST
    PASSED -> Kommune_Inspector [off]
Kommune_Inspector: Inspector [off]

Bookmark: Reguleringsplan - Verdi oversettelse av Arealformål
AttributeRenamer_3
    ATTR_TABLE:
      RENAME_SET_DEFAULT reguleringsformal > rp_formal = FME_NULL_VALUE
      RENAME_SET_DEFAULT objtype > plankilde = FME_NULL_VALUE
      RENAME_SET_DEFAULT planidentifikasjon > planid = FME_NULL_VALUE
    MISSING_INPUT_ATTRS = SET
    -> AttributeValueMapper_10
AttributeRenamer_4
    ATTR_TABLE:
      RENAME_SET_DEFAULT arealformal > rp_formal = FME_NULL_VALUE
      RENAME_SET_DEFAULT objtype > plankilde = FME_NULL_VALUE
      RENAME_SET_DEFAULT planidentifikasjon > planid = FME_NULL_VALUE
    MISSING_INPUT_ATTRS = SET
    -> AttributeValueMapper_10
Note: Reguleringsplan - Klargjøring før kobling med øvrige plandata / Oversetting av reguleringsformal og arealformal til Arealformål verdier med bruk av reguleringsplankobling: / rp_formal --> arealformalkode
AttributeValueMapper_10
    LUT = 100,1001,1000,1001,1001,1001,110,1110,111,1110,1110,1110,1111,1110,1112,1110,1113,1110,1119,2080,112,1110,1120,1120,1121,1120,1122,1120,1123,1120,1124,1120,113,1110,1130,1130,1140,1140,115,1110,1150,1150,1160,1160,1161,1160,1162,1160,1163,1160,1164,1160,1165,1160,1166,1160,1167,1160,1168,1160,1169,1160,1170,1170,1171,1170,1172,1170,1173,1170,1174,1170,120,1150,1200,1200,1201,1200,130,1300,1300,1300,1310,1300,1320,1300,1330,1300,1340,1300,1350,1300,1360,1300,1390,1300,140,1300,1400,1400,1410,1400,1420,1400,1430,1400,1440,1400,1450,1400,1460,1400,1470,1400,1490,1400,150,1120,1500,1500,1501,1500,1502,1500,1510,1500,1520,1500,1530,1500,1540,1500,1541,1500,1542,1500,1550,1500,1560,1500,1570,1500,1587,6230,1588,6230,1589,1500,1590,1500,160,1160,1600,1600,1610,1600,162,1160,1620,1600,163,1160,1630,1600,164,1160,166,1160,167,1160,169,1160,1690,1600,170,1160,1700,1700,1710,1700,172,1160,173,1160,1730,1700,174,1160,176,1160,177,1160,179,1160,180,1170,1800,1800,1801,1800,1802,1800,1803,1800,1804,1800,181,1170,1810,1300,1811,1300,1812,1300,1813,1300,1814,1300,182,1170,1820,1800,1821,1800,1822,1800,1823,1800,1824,1300,1825,1300,1826,1300,1830,1300,1831,1300,190,2080,1900,1800,191,2080,192,1300,199,1500,200,5100,2000,2001,2001,2001,2010,2010,2011,2010,2012,2010,2013,2001,2014,2010,2015,2010,2016,2010,2017,2001,2018,2001,2019,2001,2020,2020,2021,2020,2022,2020,2023,2020,2024,2001,2025,2001,2026,2001,2027,2001,2028,2001,2029,2001,2030,2030,2031,2030,2032,2030,2033,2030,2034,2030,2040,2040,2041,2040,2042,2040,2043,2040,2044,2044,2045,2001,2050,2050,2060,2060,2061,2060,2070,2070,2071,2070,2072,2070,2073,2070,2074,2070,2080,2080,2081,2080,2082,2080,2083,2080,210,5100,2100,2100,2101,2100,2110,2100,2120,2100,2140,2100,2141,2100,2142,2100,2143,2100,2150,2100,2160,2100,2170,2100,2180,2100,2190,2100,220,5100,230,5100,240,1600,2800,2800,2900,2800,299,5100,300,2001,3000,3002,3001,3002,3002,3002,3020,3020,3030,3030,3031,3030,3040,3040,3041,3040,3050,3050,3060,3002,3061,3002,310,2010,3100,3100,311,2010,3110,3100,319,2001,320,2010,321,2010,322,2010,330,2010,331,2001,332,2080,333,2080,340,2060,341,2070,342,2070,343,2070,350,2020,360,2020,370,2030,371,2030,372,2030,380,2040,3800,3800,381,2040,382,1500,390,6200,3900,3800,391,6200,392,6220,398,6200,399,2001,400,3040,4000,4001,4001,4001,4010,4010,4020,4020,4030,4030,410,3050,420,3030,421,3030,430,3040,440,1400,450,3040,459,3040,460,6700,461,6700,462,6230,463,6700,469,6700,4800,4800,4900,4800,500,2100,5000,5100,5001,5100,510,2100,5100,5100,5110,5100,5111,5100,5112,5100,5113,5100,5114,5100,5115,5100,5120,3002,5130,3002,5140,5100,520,1400,5200,5200,5210,5210,5220,5220,5230,5230,530,1500,5300,3002,540,5100,5400,5100,550,5100,5500,3002,5600,3002,590,5100,5900,5100,600,9999,6000,6001,6001,6001,601,2010,6100,6100,611,3002,6110,6110,612,1170,6120,6120,613,3002,6130,6130,614,6700,615,1400,616,1400,617,1700,618,6230,619,6230,620,1500,6200,6200,621,1500,6210,6200,6211,6200,622,6500,6220,6220,623,1500,6230,6230,624,2100,6240,6230,625,2100,626,4001,627,1500,630,1500,6300,6300,631,6400,6310,6300,6320,6300,6330,6600,640,2001,6400,6400,641,2001,6410,6400,6420,6400,6430,6400,645,5100,646,5100,650,3002,6500,6500,651,6600,652,3002,660,9999,6600,6600,661,9999,6610,6600,662,9999,6620,6600,663,3002,670,1200,6700,6700,671,1200,6710,6700,6720,6700,6730,6230,6740,6230,6750,6230,6760,6700,6770,6700,680,5100,6800,6800,681,5100,685,1300,690,1500,6900,6800,691,2001,692,1170,693,1500,699,9999,700,1500,710,2010,720,2010,730,2080,750,1600,760,1110,770,2080,780,3002,790,1500,800,1001,900,1800,910,1800,911,1800,912,1800,913,1800,920,1300,921,1300,922,1300,923,1300,924,1300,930,1300,931,1300,939,1300,960,1160,980,1300,990,1800,991,1500,992,2001,999,9999
    MAPPING_DIRECTION = FORWARD
    SRC = rp_formal
    VAL_ATTR = arealformalkode
    -> FeatureMerger_4 [REQUESTOR]

Bookmark: RpArealformalOmrade: Reguleringsplan pbl. 2008 (POST PBL2008)
RpArealformalOmrade (reader FILEGDB_3)
    attributes: OBJECTID objectid, objtype text(32), kommunenummer text(4), planidentifikasjon text(16), arealformal int, vertikalniva smallint, eierform smallint, utnyttingstype int, utnyttingstall double, utnyttingstall_minimum double, beskrivelse text(120), feltbetegnelse text(20), uteoppholdsareal int, byggverkbestemmelse smallint, avkjorselsbestemmelse smallint, forstedigitaliseringsdato date, oppdateringsdato date, omradeid int, originaldatavert text(100), kopidato date, lokalid text(100), navnerom text(100), versjonid text(100), SHAPE_Length double, SHAPE_Area double
    -> CsmapReprojector_2
CsmapReprojector_2
    DEST = $(DEST)
    INTERPOLATION_TYPE_NAME = Nearest Neighbor
    RASTER_CELL_SIZE = Preserve Cells
    RASTER_TOLERANCE = 0.0
    REPROJECTED -> Tester_3 [off]
    REPROJECTED -> AttributeKeeper_2
AttributeKeeper_2
    CREATE_BULK_MODE_FEATURES = NO
    KEEP_ATTRS = arealformal,objtype,planidentifikasjon,kommunenummer
    -> AttributeRenamer_4
Tester_3 [off]
    BOOL_OP = OR
    TEST_CLAUSE = NUM_TEST @Value(kommunenummer) IN $(Kommune)
    TEST_MODE = NUM_TEST
    PASSED -> Kommune_Inspector_2 [off]
Kommune_Inspector_2: Inspector [off]

Bookmark: RpOmrade: Fellesegenskaper Planområde
RpOmrade (reader FILEGDB_3)
    attributes: OBJECTID objectid, objtype text(32), kommunenummer text(4), planidentifikasjon text(16), plannavn text(120), plantype smallint, planstatus smallint, planbestemmelse smallint, vertikalniva smallint, lovreferanse smallint, ikrafttredelsesdato date, lovreferansebeskrivelse text(120), forslagsstillertype smallint, vedtakendeligplandato date, kunngjoringsdato date, opprinneligadministrativenhet text(4), opprinneligplanid text(16), forstedigitaliseringsdato date, oppdateringsdato date, informasjon text(255), link text(255), prosesshistorie text(255), omradeid int, originaldatavert text(100), kopidato date, lokalid text(100), navnerom text(100), versjonid text(100), SHAPE_Length double, SHAPE_Area double
    -> CsmapReprojector_14
CsmapReprojector_14
    DEST = $(DEST)
    INTERPOLATION_TYPE_NAME = Nearest Neighbor
    RASTER_CELL_SIZE = Preserve Cells
    RASTER_TOLERANCE = 0.0
    REPROJECTED -> Tester_24 [off]
    REPROJECTED -> AttributeKeeper_17
AttributeKeeper_17
    CREATE_BULK_MODE_FEATURES = NO
    KEEP_ATTRS = ikrafttredelsesdato,planidentifikasjon,kommunenummer,lovreferanse,planbestemmelse,plannavn,planstatus,plantype
    -> FeatureMerger_4 [SUPPLIER]
Tester_24 [off]
    BOOL_OP = OR
    TEST_CLAUSE = NUM_TEST @Value(kommunenummer) IN $(Kommune)
    TEST_MODE = NUM_TEST
    PASSED -> Kommune_Inspector_3 [off]
Kommune_Inspector_3: Inspector [off]

Bookmark: Fjerner overlappende reguleringsplaner (behold nyeste plan)
Note: Slå sammen fellesegenskaper med rp post og pre pbl. 2008 basert på planid og kommunenr.
FeatureMerger_4
    ATTR_ACCUM_MODE = Merge Supplier
    ATTR_CONFLICT_RES = Use Requestor
    IGNORE_NULLS = No
    JOIN_KEYS = @Value(planid) @Value(planidentifikasjon) AUTO @Value(kommunenummer) @Value(kommunenummer) AUTO
    MERGE_TYPE = Attributes Only
    PROCESS_DUPS = NO
    REJECT_NULL_MISSING_KEYS = No
    SUPPLIERS_FIRST = No
    MERGED -> AreaOnAreaOverlayer_4 [AREA]
    MERGED -> Clipper [CANDIDATE]
    UNMERGED_REQUESTOR -> Clipper [CANDIDATE]
Note: Beregn antall overlappende planer
AreaOnAreaOverlayer_4
    ACCUM_ATTRS_NAME = Merge Incoming Attributes
    CLEANING_TOLERANCE = Automatic
    CONNECT_Z_MODE = First Wins
    DEAGGREGATE_INPUT = Yes
    LIST_ATTRS_TO_INCLUDE = ikrafttredelsesdato kommunenummer planidentifikasjon arealformalkode lovreferanse planbestemmelse planid plankilde plannavn planstatus plantype rp_formal
    LIST_NAME = attri
    OVC_ATTR = _overlaps
    AREA -> UUIDGenerator_2
UUIDGenerator_2
    UUID_ATTR = _uuid
    UUID_FORMAT = UUID_ONLY
    -> ListExploder
ListExploder
    ATTR_ACCUM_MODE = Prefix List Attributes
    INCOMING_PREFIX = _attri_
    INDEX_ATTR = _element_index
    LIST_ATTR = attri{}
    ELEMENTS -> Tester_16
Note: Test planoverlapp: / 1 = no overlapp / > 1 = overlapp (pass)
Tester_16
    BOOL_OP = OR
    TEST_CLAUSE = TEST @Value(_overlaps) > 1
    TEST_MODE = TEST
    PASSED -> BulkAttributeRemover_3
BulkAttributeRemover_3
    ATTR_EXP = \b[^_]\w+
    -> Sorter
Note: sorter etter ikraftredelsedato (descending)
Sorter
    SORT_PARM = _attri_ikrafttredelsesdato NUMERIC DESCENDING
    SORTED -> Sampler
Note: behold nyeste plan
Sampler
    GROUP_BY = _uuid
    RATE = 1
    SAMPLE_MODE = No
    SAMPLE_TYPE_LONG = First N Features
    SAMPLED -> AttributeRemover_2
AttributeRemover_2
    REMOVE_ATTRS = _element_index,_attri_planidentifikasjon,_uuid
    -> BulkAttributeRenamer
BulkAttributeRenamer
    ATTRCHOICE = All Attributes
    CASE_DISP = YES
    MODE_CHOICE = RENAME
    PATTERN_ACTION_DISP = REMOVEPREFIX
    REPLACE_STR = _attri_
    -> Dissolver_4
Dissolver_4
    ACCUM_INPUT_ATTRS = Use Attributes From One Feature
    CLEANING_TOLERANCE = Automatic
    CONNECT_Z_MODE = First Wins
    DEAGGREGATE_INPUT = Yes
    GROUP_BY = kommunenummer planid _overlaps arealformalkode fme_feature_type ikrafttredelsesdato lovreferanse planbestemmelse plankilde plannavn planstatus plantype rp_formal
    AREA -> Clipper [CLIPPER]
    AREA -> Junction_22
Note: Klipp bort planområder som overlapper.
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Junction_22
Note: Legg till den nyeste plan av de overlappende planer.
Junction_22
    -> AttributeKeeper_18
AttributeKeeper_18
    CREATE_BULK_MODE_FEATURES = NO
    KEEP_ATTRS = arealformalkode,ikrafttredelsesdato,kommunenummer,lovreferanse,planbestemmelse,planid,plankilde,plannavn,planstatus,plantype,rp_formal,_overlaps
    -> NullAttributeMapper
NullAttributeMapper
    ATTRCHOICE = Selected Attributes
    ATTRLIST = _overlaps
    NEW_VALUE = 1
    NULL_TREATMENT = New Value
    SOURCE_ATTR_VAL = Null Empty "Missing (Selected Attributes Only)"
    -> FeatureMerger_3 [REQUESTOR]

Bookmark: Kobling for å utelate gitte regplaner
FeatureMerger_3
    ATTR_ACCUM_MODE = Merge Supplier
    ATTR_CONFLICT_RES = Use Requestor
    IGNORE_NULLS = No
    JOIN_KEYS = @Value(planid) @Value(Planid) AUTO
    MERGE_TYPE = Attributes Only
    PROCESS_DUPS = NO
    REJECT_NULL_MISSING_KEYS = No
    SUPPLIERS_FIRST = No
    UNMERGED_REQUESTOR -> AttributeManager

Bookmark: CSV Renset Reguleringsplaner
AttributeManager
    ATTR_TABLE = RENAME_SET_VALUE _overlaps > rp_overlapp
    -> AreaOnAreaOverlayer_2 [AREA]
    -> Reguleringsplaner
    -> renset_reguleringsplaner_2023 (writer CSV2_1)
renset_reguleringsplaner_2023 (writer CSV2_1)
    attributes: plankilde varchar(32), planid varchar(16), rp_formal string, arealformalkode string, plannavn varchar(120), plantype string, planstatus string, planbestemmelse string, lovreferanse string, ikrafttredelsesdato datetime, rp_overlapp uint32, kommunenummer varchar(4)
Reguleringsplaner: Inspector

Bookmark: Arealformålsgruppe
Note: Arealformålsgruppe
AttributeValueMapper_7
    LUT = 1001,01 Bolig eller sentrumsformål,1110,01 Bolig eller sentrumsformål,1120,02 Fritidsbebyggelse,1130,01 Bolig eller sentrumsformål,1140,04 Handel,1150,04 Handel,1160,03 Tjenesteyting,1170,05 Turistformål,1200,07 Råstoffutvinning,1300,06 Næringsvirksomhet,1400,09 Idrettsanlegg,1500,10 Andre formål,1600,10 Andre formål,1700,10 Andre formål,1800,08 Kombinerte formål,2001,11 Samferdselsanlegg,2010,11 Samferdselsanlegg,2020,11 Samferdselsanlegg,2030,11 Samferdselsanlegg,2040,16 Havner og småbåthavner,2044,16 Havner og småbåthavner,2050,11 Samferdselsanlegg,2060,11 Samferdselsanlegg,2070,11 Samferdselsanlegg,2080,11 Samferdselsanlegg,2100,11 Samferdselsanlegg,2800,11 Samferdselsanlegg,3002,12 Blå/grønnstruktur,3020,12 Blå/grønnstruktur,3030,12 Blå/grønnstruktur,3040,12 Blå/grønnstruktur,3050,12 Blå/grønnstruktur,3100,12 Blå/grønnstruktur,3800,12 Blå/grønnstruktur,4001,13 Forsvaret,4010,13 Forsvaret,4020,13 Forsvaret,4030,13 Forsvaret,4800,13 Forsvaret,5100,14 LNFR,5200,15 LNFR spredt,5210,15 LNFR spredt,5220,15 LNFR spredt,5230,15 LNFR spredt,6001,17 Sjø og vassdrag, flerbruk,6100,17 Sjø og vassdrag, flerbruk,6110,17 Sjø og vassdrag, flerbruk,6120,17 Sjø og vassdrag, flerbruk,6130,17 Sjø og vassdrag, flerbruk,6200,17 Sjø og vassdrag, flerbruk,6220,16 Havner og småbåthavner,6230,16 Havner og småbåthavner,6300,17 Sjø og vassdrag, flerbruk,6400,18 Akvakultur,6500,17 Sjø og vassdrag, flerbruk,6600,17 Sjø og vassdrag, flerbruk,6700,17 Sjø og vassdrag, flerbruk,6800,17 Sjø og vassdrag, flerbruk,9999,19 Udefinert
    MAPPING_DIRECTION = FORWARD
    SRC = arealformalkode
    VAL_ATTR = arealformalsgruppe
    -> AttributeValueMapper_2
Note: Arealformål
AttributeValueMapper_2
    LUT = 1001,1001 - Bebyggelse og anlegg,1110,1110 - Boligbebyggelse,1120,1120 - Fritidsbebyggelse,1130,1130 - Sentrumsformål,1140,1140 - Kjøpesenter,1150,1150 - Forretninger,1160,1160 - Offentlig eller privat tjenesteyting,1170,1170 - Fritids- og turistformål,1200,1200 - Råstoffutvinning,1300,1300 - Næringsvirksomhet,1400,1400 - Idrettsanlegg,1500,1500 - Andre typer nærmere angitt bebyggelse og anlegg,1600,1600 - Uteoppholdsareal,1700,1700 - Grav-og urnelund,1800,1800 - Kombinert bebyggelse og anleggsformål,2001,2001 - Samferdselsanlegg og teknisk infrastruktur (arealer),2010,2010 - Veg,2020,2020 - Bane,2030,2030 - Lufthavn,2040,2040 - Havn,2044,2044 - Molo,2050,2050 - Hovednett for sykkel,2060,2060 - Kollektivnett,2070,2070 - Kollektivknutepunkt,2080,2080 - Parkeringsanlegg,2100,2100 - Trase for tekn. infrastr.,2800,2800 - Kombinerte formål samf., infrastr.,3002,3002 - Blå/grønnstruktur,3020,3020 - Naturområde,3030,3030 - Turdrag,3040,3040 - Friområde,3050,3050 - Park,3100,3100 - Overvannstiltak,3800,3800 - Kombinerte grøntstrukturformål,4001,4001 - Forsvaret,4010,4010 - Ulike typer militære formål,4020,4020 - Skytefelt/øvingsområde,4030,4030 - Forlegning/leir,4800,4800 - Kombinerte militærformål,5100,5100 - LNRF - tiltak for stedbunden næring,5200,5200 - LNFR - spredt bolig- fritids eller næringsbebyggelse,5210,5210 - Spredt boligbebyggelse,5220,5220 - Spredt fritidsbebyggelse,5230,5230 - Spredt næringsbebyggelse,6001,6001 - Bruk og vern av sjø, vassdrag, strandsone,6100,6100 - Sjø, vassdrag - Ferdsel,6110,6110 - Ankringsområder,6120,6120 - Opplagsområde,6130,6130 - Riggområde,6200,6200 - Sjø, vassdrag - Farleder,6220,6220 - Havneområde i sjø,6230,6230 - Sjø, vassdrag - Småbåthavn,6300,6300 - Sjø, vassdrag - Fiske,6400,6400 - Sjø, vassdrag - Akvakultur,6500,6500 - Sjø, vassdrag - Drikkevann,6600,6600 - Sjø, vassdrag - Naturområde,6700,6700 - Sjø, vassdrag - Friluftsområde,6800,6800 - Sjø, vassdrag - Kombinerte formål,9999,9999 - Udefinert
    MAPPING_DIRECTION = FORWARD
    SRC = arealformalkode
    VAL_ATTR = arealformal
    -> DateTimeStamper

Bookmark: Admin
Note: planmosaikkdato
DateTimeStamper
    DATETIME_ATTR = plannmosaikkdato
    STAMP_TYPE = date
    TIMEZONE = utc
    -> AttributeRenamer
Note: kommunenavn
AttributeValueMapper_3
    LUT = 1101,EIGERSUND,1850,NARVIK,5012,HEIM,1103,STAVANGER,1106,HAUGESUND,1108,SANDNES,1111,SOKNDAL,1112,LUND,1114,BJERKREIM,1119,HÅ,1120,KLEPP,1121,TIME,1122,GJESDAL,1124,SOLA,1127,RANDABERG,1130,STRAND,1133,HJELMELAND,1134,SULDAL,1135,SAUDA,1144,KVITSØY,1145,BOKN,1146,TYSVÆR,1149,KARMØY,1151,UTSIRA,1160,VINDAFJORD,1505,KRISTIANSUND,1506,MOLDE,1507,ÅLESUND,1511,VANYLVEN,1514,SANDE,1515,HERØY,1516,ULSTEIN,1517,HAREID,1520,ØRSTA,1525,STRANDA,1528,SYKKYLVEN,1531,SULA,1532,GISKE,1535,VESTNES,1539,RAUMA,1547,AUKRA,1554,AVERØY,1557,GJEMNES,1560,TINGVOLL,1563,SUNNDAL,1566,SURNADAL,1573,SMØLA,1576,AURE,1577,VOLDA,1578,FJORD,1579,HUSTADVIKA,1804,BODØ,1806,NARVIK,1811,BINDAL,1812,SØMNA,1813,BRØNNØY,1815,VEGA,1816,VEVELSTAD,1818,HERØY,1820,ALSTAHAUG,1822,LEIRFJORD,1824,VEFSN,1825,GRANE,1826,HATTFJELLDAL,1827,DØNNA,1828,NESNA,1832,HEMNES,1833,RANA,1834,LURØY,1835,TRÆNA,1836,RØDØY,1837,MELØY,1838,GILDESKÅL,1839,BEIARN,1840,SALTDAL,1841,FAUSKE,1845,SØRFOLD,1848,STEIGEN,1851,LØDINGEN,1853,EVENES,1856,RØST,1857,VÆRØY,1859,FLAKSTAD,1860,VESTVÅGØY,1865,VÅGAN,1866,HADSEL,1867,BØ,1868,ØKSNES,1870,SORTLAND,1871,ANDØY,1874,MOSKENES,1875,HAMARØY,3001,HALDEN,3002,MOSS,3003,SARPSBORG,3004,FREDRIKSTAD,3005,DRAMMEN,3006,KONGSBERG,3007,RINGERIKE,301,OSLO,3011,HVALER,3012,AREMARK,3013,MARKER,3014,INDRE ØSTFOLD,3015,SKIPTVET,3016,RAKKESTAD,3017,RÅDE,3018,VÅLER (VIKEN),3019,VESTBY,3020,NORDRE FOLLO,3021,ÅS,3022,FROGN,3023,NESODDEN,3024,BÆRUM,3025,ASKER,3026,AURSKOG-HØLAND,3027,RÆLINGEN,3028,ENEBAKK,3029,LØRENSKOG,3030,LILLESTRØM,3031,NITTEDAL,3032,GJERDRUM,3033,ULLENSAKER,3034,NES,3035,EIDSVOLL,3036,NANNESTAD,3037,HURDAL,3038,HOLE,3039,FLÅ,3040,NESBYEN,3041,GOL,3042,HEMSEDAL,3043,ÅL,3044,HOL,3045,SIGDAL,3046,KRØDSHERAD,3047,MODUM,3048,ØVRE EIKER,3049,LIER,3050,FLESBERG,3051,ROLLAG,3052,NORE OG UVDAL,3053,JEVNAKER,3054,LUNNER,3401,KONGSVINGER,3403,HAMAR,3405,LILLEHAMMER,3407,GJØVIK,3411,RINGSAKER,3412,LØTEN,3413,STANGE,3414,NORD-ODAL,3415,SØR-ODAL,3416,EIDSKOG,3417,GRUE,3418,ÅSNES,3419,VÅLER (INNLANDET),3420,ELVERUM,3421,TRYSIL,3422,ÅMOT,3423,STOR-ELVDAL,3424,RENDALEN,3425,ENGERDAL,3426,TOLGA,3427,TYNSET,3428,ALVDAL,3429,FOLLDAL,3430,OS (INNLANDET),3431,DOVRE,3432,LESJA,3433,SKJÅK,3434,LOM,3435,VÅGÅ,3436,NORD-FRON,3437,SEL,3438,SØR-FRON,3439,RINGEBU,3440,ØYER,3441,GAUSDAL,3442,ØSTRE TOTEN,3443,VESTRE TOTEN,3446,GRAN,3447,SØNDRE LAND,3448,NORDRE LAND,3449,SØR-AURDAL,3450,ETNEDAL,3451,NORD-AURDAL,3452,VESTRE SLIDRE,3453,ØYSTRE SLIDRE,3454,VANG,3801,HORTEN,3802,HOLMESTRAND,3803,TØNSBERG,3804,SANDEFJORD,3805,LARVIK,3806,PORSGRUNN,3807,SKIEN,3808,NOTODDEN,3811,FÆRDER,3812,SILJAN,3813,BAMBLE,3814,KRAGERØ,3815,DRANGEDAL,3816,NOME,3817,MIDT-TELEMARK,3818,TINN,3819,HJARTDAL,3820,SELJORD,3821,KVITESEID,3822,NISSEDAL,3823,FYRESDAL,3824,TOKKE,3825,VINJE,4201,RISØR,4202,GRIMSTAD,4203,ARENDAL,4204,KRISTIANSAND,4205,LINDESNES,4206,FARSUND,4207,FLEKKEFJORD,4211,GJERSTAD,4212,VEGÅRSHEI,4213,TVEDESTRAND,4214,FROLAND,4215,LILLESAND,4216,BIRKENES,4217,ÅMLI,4218,IVELAND,4219,EVJE OG HORNNES,4220,BYGLAND,4221,VALLE,4222,BYKLE,4223,VENNESLA,4224,ÅSERAL,4225,LYNGDAL,4226,HÆGEBOSTAD,4227,KVINESDAL,4228,SIRDAL,4601,BERGEN,4602,KINN,4611,ETNE,4612,SVEIO,4613,BØMLO,4614,STORD,4615,FITJAR,4616,TYSNES,4617,KVINNHERAD,4618,ULLENSVANG,4619,EIDFJORD,4620,ULVIK,4621,VOSS,4622,KVAM,4623,SAMNANGER,4624,BJØRNAFJORDEN,4625,AUSTEVOLL,4626,ØYGARDEN,4627,ASKØY,4628,VAKSDAL,4629,MODALEN,4630,OSTERØY,4631,ALVER,4632,AUSTRHEIM,4633,FEDJE,4634,MASFJORDEN,4635,GULEN,4636,SOLUND,4637,HYLLESTAD,4638,HØYANGER,4639,VIK,4640,SOGNDAL,4641,AURLAND,4642,LÆRDAL,4643,ÅRDAL,4644,LUSTER,4645,ASKVOLL,4646,FJALER,4647,SUNNFJORD,4648,BREMANGER,4649,STAD,4650,GLOPPEN,4651,STRYN,5001,TRONDHEIM,5006,STEINKJER,5007,NAMSOS,5014,FRØYA,5020,OSEN,5021,OPPDAL,5022,RENNEBU,5025,RØROS,5026,HOLTÅLEN,5027,MIDTRE GAULDAL,5028,MELHUS,5029,SKAUN,5031,MALVIK,5032,SELBU,5033,TYDAL,5034,MERÅKER,5035,STJØRDAL,5036,FROSTA,5037,LEVANGER,5038,VERDAL,5041,SNÅSA,5042,LIERNE,5043,RØYRVIK,5044,NAMSSKOGAN,5045,GRONG,5046,HØYLANDET,5047,OVERHALLA,5049,FLATANGER,5052,LEKA,5053,INDERØY,5054,INDRE FOSEN,5055,HEIM,5056,HITRA,5057,ØRLAND,5058,ÅFJORD,5059,ORKLAND,5060,NÆRØYSUND,5061,RINDAL,5401,TROMSØ,5402,HARSTAD,5403,ALTA,5404,VARDØ,5405,VADSØ,5406,HAMMERFEST,5411,KVÆFJORD,5412,TJELDSUND,5413,IBESTAD,5414,GRATANGEN,5415,LAVANGEN,5416,BARDU,5417,SALANGEN,5418,MÅLSELV,5419,SØRREISA,5420,DYRØY,5421,SENJA,5422,BALSFJORD,5423,KARLSØY,5424,LYNGEN,5425,STORFJORD,5426,KÅFJORD,5427,SKJERVØY,5428,NORDREISA,5429,KVÆNANGEN,5430,KAUTOKEINO,5432,LOPPA,5433,HASVIK,5434,MÅSØY,5435,NORDKAPP,5436,PORSANGER,5437,KARASJOK,5438,LEBESBY,5439,GAMVIK,5440,BERLEVÅG,5441,TANA,5442,NESSEBY,5443,BÅTSFJORD,5444,SØR-VARANGER
    MAPPING_DIRECTION = FORWARD
    SRC = kommunenr_2020
    VAL_ATTR = kommune
    -> AttributeValueMapper_4
Note: fylkesnummer
AttributeValueMapper_4
    LUT = 1101,11,1103,11,1106,11,1108,11,1111,11,1112,11,1114,11,1119,11,1120,11,1121,11,1122,11,1124,11,1127,11,1130,11,1133,11,1134,11,1135,11,1144,11,1145,11,1146,11,1149,11,1151,11,1160,11,1505,15,1506,15,1507,15,1511,15,1514,15,1515,15,1516,15,1517,15,1520,15,1525,15,1528,15,1531,15,1532,15,1535,15,1539,15,1547,15,1554,15,1557,15,1560,15,1563,15,1566,15,1573,15,1576,15,1577,15,1578,15,1579,15,1804,18,1806,18,1811,18,1812,18,1813,18,1815,18,1816,18,1818,18,1820,18,1822,18,1824,18,1825,18,1826,18,1827,18,1828,18,1832,18,1833,18,1834,18,1835,18,1836,18,1837,18,1838,18,1839,18,1840,18,1841,18,1845,18,1848,18,1851,18,1853,18,1856,18,1857,18,1859,18,1860,18,1865,18,1866,18,1867,18,1868,18,1870,18,1871,18,1874,18,1875,18,3001,30,3002,30,3003,30,3004,30,3005,30,3006,30,3007,30,301,3,3011,30,3012,30,3013,30,3014,30,3015,30,3016,30,3017,30,3018,30,3019,30,3020,30,3021,30,3022,30,3023,30,3024,30,3025,30,3026,30,3027,30,3028,30,3029,30,3030,30,3031,30,3032,30,3033,30,3034,30,3035,30,3036,30,3037,30,3038,30,3039,30,3040,30,3041,30,3042,30,3043,30,3044,30,3045,30,3046,30,3047,30,3048,30,3049,30,3050,30,3051,30,3052,30,3053,30,3054,30,3401,34,3403,34,3405,34,3407,34,3411,34,3412,34,3413,34,3414,34,3415,34,3416,34,3417,34,3418,34,3419,34,3420,34,3421,34,3422,34,3423,34,3424,34,3425,34,3426,34,3427,34,3428,34,3429,34,3430,34,3431,34,3432,34,3433,34,3434,34,3435,34,3436,34,3437,34,3438,34,3439,34,3440,34,3441,34,3442,34,3443,34,3446,34,3447,34,3448,34,3449,34,3450,34,3451,34,3452,34,3453,34,3454,34,3801,38,3802,38,3803,38,3804,38,3805,38,3806,38,3807,38,3808,38,3811,38,3812,38,3813,38,3814,38,3815,38,3816,38,3817,38,3818,38,3819,38,3820,38,3821,38,3822,38,3823,38,3824,38,3825,38,4201,42,4202,42,4203,42,4204,42,4205,42,4206,42,4207,42,4211,42,4212,42,4213,42,4214,42,4215,42,4216,42,4217,42,4218,42,4219,42,4220,42,4221,42,4222,42,4223,42,4224,42,4225,42,4226,42,4227,42,4228,42,4601,46,4602,46,4611,46,4612,46,4613,46,4614,46,4615,46,4616,46,4617,46,4618,46,4619,46,4620,46,4621,46,4622,46,4623,46,4624,46,4625,46,4626,46,4627,46,4628,46,4629,46,4630,46,4631,46,4632,46,4633,46,4634,46,4635,46,4636,46,4637,46,4638,46,4639,46,4640,46,4641,46,4642,46,4643,46,4644,46,4645,46,4646,46,4647,46,4648,46,4649,46,4650,46,4651,46,5001,50,5006,50,5007,50,5014,50,5020,50,5021,50,5022,50,5025,50,5026,50,5027,50,5028,50,5029,50,5031,50,5032,50,5033,50,5034,50,5035,50,5036,50,5037,50,5038,50,5041,50,5042,50,5043,50,5044,50,5045,50,5046,50,5047,50,5049,50,5052,50,5053,50,5054,50,5055,50,5056,50,5057,50,5058,50,5059,50,5060,50,5061,50,5401,54,5402,54,5403,54,5404,54,5405,54,5406,54,5411,54,5412,54,5413,54,5414,54,5415,54,5416,54,5417,54,5418,54,5419,54,5420,54,5421,54,5422,54,5423,54,5424,54,5425,54,5426,54,5427,54,5428,54,5429,54,5430,54,5432,54,5433,54,5434,54,5435,54,5436,54,5437,54,5438,54,5439,54,5440,54,5441,54,5442,54,5443,54,5444,54
    MAPPING_DIRECTION = FORWARD
    SRC = kommunenr_2020
    VAL_ATTR = fylkesnummer
    -> AttributeValueMapper_5
Note: fylkesnavn
AttributeValueMapper_5
    LUT = 11,ROGALAND,15,MØRE OG ROMSDAL,18,NORDLAND,3,OSLO,30,VIKEN,34,INNLANDET,38,VESTFOLD OG TELEMARK,42,AGDER,46,VESTLAND,50,TRØNDELAG,54,TROMS OG FINNMARK
    MAPPING_DIRECTION = FORWARD
    SRC = fylkesnummer
    VAL_ATTR = fylke
    -> StringCaseChanger
StringCaseChanger
    ATTRCHOICE = Selected Attributes
    ATTRLIST = fylke kommune
    CHANGE_TYPE = Title case
    -> AttributeRenamer_2
AttributeRenamer_2
    ATTR_TABLE = RENAME_SET_DEFAULT kommunenr_2020 > kommunenummer
    MISSING_INPUT_ATTRS = REMOVE
    -> AttributeCreator
Note: plan_overlapp
AttributeCreator
    ATTR_TABLE = SET_TO plan_overlapp = kommuneplan: @Value(kp_overlapp); reguleringsplan: @Value(rp_overlapp)
    -> Dissolver_3
Dissolver_3
    ACCUM_INPUT_ATTRS = Use Attributes From One Feature
    CLEANING_TOLERANCE = Automatic
    CONNECT_Z_MODE = First Wins
    DEAGGREGATE_INPUT = Yes
    GROUP_BY = arealformal arealformalkode arealformalsgruppe kommunenummer kp_formal planid rp_formal plannmosaikkdato kp_overlapp rp_overlapp omradenavn arealstatus plannavn plantype planbestemmelse planstatus lovreferanse ikrafttredelsesdato kommune fylkesnummer fylke plan_overlapp plankilde
    AREA -> AreaCalculator
Note: planlagt_areal_,m2
AreaCalculator
    AREA_ATTR = planlagt_areal_m2
    AREA_TYPE = Plane Area
    MULT = 1
    -> AttributeRounder
AttributeRounder
    PLACES = 2
    ROUND_TYPE = Nearest
    SRC_ATTRS = planlagt_areal_m2
    -> AttributeManager_5
AttributeManager_5
    ATTR_TABLE:
      REMOVE kp_overlapp
      REMOVE rp_overlapp
    -> Junction_2

Bookmark: ensure kommenummer = 2020
AttributeRenamer
    ATTR_TABLE = RENAME_SET_DEFAULT kommunenummer > kommunenr_gammel
    MISSING_INPUT_ATTRS = REMOVE
    -> AttributeValueMapper
AttributeValueMapper
    LUT = 1001,4204,1002,4205,1003,4206,1004,4207,101,3001,1014,4223,1017,4204,1018,4204,1021,4205,1026,4224,1027,4225,1029,4205,1032,4225,1034,4226,1037,4227,104,3002,1046,4228,105,3003,106,3004,1101,1101,1102,1108,1103,1103,1106,1106,111,3011,1111,1111,1112,1112,1114,1114,1119,1119,1120,1120,1121,1121,1122,1122,1124,1124,1127,1127,1129,1108,1130,1130,1133,1133,1134,1134,1135,1135,1141,1103,1142,1103,1144,1144,1145,1145,1146,1146,1149,1149,1151,1151,1160,1160,118,3012,119,3013,1201,4601,121,3026,1211,4611,1216,4612,1219,4613,122,3014,1221,4614,1222,4615,1223,4616,1224,4617,1227,4618,1228,4618,123,3014,1231,4618,1232,4619,1233,4620,1234,4621,1235,4621,1238,4622,124,3014,1241,4624,1242,4623,1243,4624,1244,4625,1245,4626,1246,4626,1247,4627,125,3014,1251,4628,1252,4629,1253,4630,1256,4631,1259,4626,1260,4631,1263,4631,1264,4632,1265,4633,1266,4634,127,3015,128,3016,135,3017,136,3002,137,3018,138,3014,1401,4602,1411,4635,1412,4636,1413,4637,1416,4638,1417,4639,1418,4640,1419,4640,1420,4640,1421,4641,1422,4642,1424,4643,1426,4644,1428,4645,1429,4646,1430,4647,1431,4647,1432,4647,1433,4647,1438,4648,1439,4602,1441,4649,1443,4649,1444,1577,1445,4650,1449,4651,1502,1506,1504,1507,1505,1505,1511,1511,1514,1514,1515,1515,1516,1516,1517,1517,1519,1577,1520,1520,1523,1507,1524,1578,1525,1525,1526,1578,1528,1528,1529,1507,1531,1531,1532,1532,1534,1507,1535,1535,1539,1539,1543,1506,1545,1506,1546,1507,1547,1547,1548,1579,1551,1579,1554,1554,1557,1557,1560,1560,1563,1563,1566,1566,1571,5055,1573,1573,1576,1576,1804,1804,1805,1806,1811,1811,1812,1812,1813,1813,1815,1815,1816,1816,1818,1818,1820,1820,1822,1822,1824,1824,1825,1825,1826,1826,1827,1827,1828,1828,1832,1832,1833,1833,1834,1834,1835,1835,1836,1836,1837,1837,1838,1838,1839,1839,1840,1840,1841,1841,1845,1845,1848,1848,1849,1875,1850,1806,1850,1875,1851,1851,1852,5412,1853,1853,1854,1806,1856,1856,1857,1857,1859,1859,1860,1860,1865,1865,1866,1866,1867,1867,1868,1868,1870,1870,1871,1871,1874,1874,1902,5401,1903,5402,1911,5411,1913,5412,1917,5413,1919,5414,1920,5415,1922,5416,1923,5417,1924,5418,1925,5419,1926,5420,1927,5421,1928,5421,1929,5421,1931,5421,1933,5422,1936,5423,1938,5424,1939,5425,1940,5426,1941,5427,1942,5428,1943,5429,2002,5404,2003,5405,2004,5406,2011,5430,2012,5403,2014,5432,2015,5433,2017,5406,2018,5434,2019,5435,2020,5436,2021,5437,2022,5438,2023,5439,2024,5440,2025,5441,2027,5442,2028,5443,2030,5444,211,3019,213,3020,214,3021,215,3022,216,3023,217,3020,219,3024,220,3025,221,3026,226,3030,227,3030,228,3027,229,3028,230,3029,231,3030,233,3031,234,3032,235,3033,236,3034,237,3035,238,3036,239,3037,301,301,402,3401,403,3403,412,3411,415,3412,417,3413,418,3414,419,3415,420,3416,423,3417,425,3418,426,3419,427,3420,428,3421,429,3422,430,3423,432,3424,434,3425,436,3426,437,3427,438,3428,439,3429,441,3430,5001,5001,5004,5006,5005,5007,501,3405,5011,5055,5012,5055,5012,5056,5012,5059,5013,5056,5014,5014,5015,5057,5016,5059,5017,5057,5018,5058,5019,5058,502,3407,5020,5020,5021,5021,5022,5022,5023,5059,5024,5059,5025,5025,5026,5026,5027,5027,5028,5028,5029,5029,5030,5001,5031,5031,5032,5032,5033,5033,5034,5034,5035,5035,5036,5036,5037,5037,5038,5038,5039,5006,5040,5007,5041,5041,5042,5042,5043,5043,5044,5044,5045,5045,5046,5046,5047,5047,5048,5007,5049,5049,5050,5060,5051,5060,5052,5052,5053,5053,5054,5054,5061,5061,511,3431,512,3432,513,3433,514,3434,515,3435,516,3436,517,3437,519,3438,520,3439,521,3440,522,3441,528,3442,529,3443,532,3053,533,3054,534,3446,536,3447,538,3448,540,3449,541,3450,542,3451,543,3452,544,3453,545,3454,602,3005,604,3006,605,3007,612,3038,615,3039,616,3040,617,3041,618,3042,619,3043,620,3044,621,3045,622,3046,623,3047,624,3048,625,3005,626,3049,627,3025,628,3025,631,3050,632,3051,633,3052,701,3801,704,3803,710,3804,711,3005,712,3805,713,3802,715,3802,716,3803,729,3811,805,3806,806,3807,807,3808,811,3812,814,3813,815,3814,817,3815,819,3816,821,3817,822,3817,826,3818,827,3819,828,3820,829,3821,830,3822,831,3823,833,3824,834,3825,901,4201,904,4202,906,4203,911,4211,912,4212,914,4213,919,4214,926,4215,928,4216,929,4217,935,4218,937,4219,938,4220,940,4221,941,4222
    MAPPING_DIRECTION = FORWARD
    SRC = kommunenr_gammel
    VAL_ATTR = kommunenr_2020
    -> AttributeManager_4
AttributeManager_4
    ATTR_TABLE:
      SET_TO kp_overlapp = FME_CONDITIONAL:DEFAULT_VALUE'_FME_NO_OP_'BOOL_OP;OR;COMPOSITE_TEST;1 OR 2 OR 3;TEST kp_overlapp ATTRIBUTE_VALUE_NULL _FME_BLANK_STRING_;TEST kp_overlapp ATTRIBUTE_IS_EMPTY _FME_BLANK_STRING_;TEST kp_overlapp ATTRIBUTE_IS_MISSING _FME_BLANK_STRING_'0'FME_NUM_CONDITIONS2___
      SET_TO rp_overlapp = FME_CONDITIONAL:DEFAULT_VALUE'_FME_NO_OP_'BOOL_OP;OR;COMPOSITE_TEST;1 OR 2 OR 3;TEST rp_overlapp ATTRIBUTE_VALUE_NULL _FME_BLANK_STRING_;TEST rp_overlapp ATTRIBUTE_IS_EMPTY _FME_BLANK_STRING_;TEST rp_overlapp ATTRIBUTE_IS_MISSING _FME_BLANK_STRING_'0'FME_NUM_CONDITIONS2___
      SET_TO kommunenr_2020 = FME_CONDITIONAL:DEFAULT_VALUE'_FME_NO_OP_'BOOL_OP;OR;COMPOSITE_TEST;1 OR 2 OR 3;TEST kommunenr_2020 ATTRIBUTE_VALUE_NULL _FME_BLANK_STRING_;TEST kommunenr_2020 ATTRIBUTE_IS_EMPTY _FME_BLANK_STRING_;TEST kommunenr_2020 ATTRIBUTE_IS_MISSING _FME_BLANK_STRING_'@Value(kommunenr_gammel)'FME_NUM_CONDITIONS2___
    USER_EXPOSED_ATTRIBUTES = kommunenummer
    -> AttributeRemover
AttributeRemover
    REMOVE_ATTRS = kommunenr_gammel
    -> AttributeValueMapper_3

Bookmark: ArealBeregninger
Note: Create MultiPolygon
Aggregator_2
    ACCUM_ATTRS_NAME = Drop Incoming Attributes
    AGGREGATE_TYPE = Homogeneous Collection (If Possible)
    GROUP_BY = planid arealformalkode planlagt_areal_m2 ikrafttredelsesdato kommunenummer plankilde arealformalsgruppe arealformal plannmosaikkdato rp_formal kp_formal plan_overlapp omradenavn arealstatus plannavn plantype planbestemmelse planstatus lovreferanse kommune fylkesnummer fylke planlagt_utbygging
    MODE = Geometry - Assemble One Level
    SEP = ,
    AGGREGATE -> AreaCalculator_2
AreaCalculator_2
    AREA_ATTR = planlagt_utbygd_areal_m2
    AREA_TYPE = Plane Area
    MULT = 1
    -> AttributeRounder_2
AttributeRounder_2
    PLACES = 0
    ROUND_TYPE = Nearest
    SRC_ATTRS = planlagt_areal_m2 planlagt_utbygd_areal_m2
    -> FeatureMerger_2 [REQUESTOR]
    -> FeatureMerger_7 [SUPPLIER]
Aggregator_4
    ACCUM_ATTRS_NAME = Drop Incoming Attributes
    AGGREGATE_TYPE = Homogeneous Collection (If Possible)
    GROUP_BY = planid arealformalkode planlagt_areal_m2 ikrafttredelsesdato kommunenummer plankilde arealformalsgruppe arealformal plannmosaikkdato rp_formal kp_formal plan_overlapp omradenavn arealstatus plannavn plantype planbestemmelse planstatus lovreferanse kommune fylkesnummer fylke planlagt_utbygging
    MODE = Geometry - Assemble One Level
    SEP = ,
    AGGREGATE -> AreaCalculator_3
AreaCalculator_3
    AREA_ATTR = bebygd_og_restareal_m2
    AREA_TYPE = Plane Area
    MULT = 1
    -> AttributeRounder_3
AttributeRounder_3
    PLACES = 0
    ROUND_TYPE = Nearest
    SRC_ATTRS = planlagt_areal_m2 bebygd_og_restareal_m2
    -> FeatureMerger_2 [SUPPLIER]
    -> FeatureMerger_7 [REQUESTOR]
Note: Slå sammen areal attributter
FeatureMerger_2
    ATTR_ACCUM_MODE = Merge Supplier
    ATTR_CONFLICT_RES = Use Requestor
    IGNORE_NULLS = No
    JOIN_KEYS = @Value(planid) @Value(planid) AUTO @Value(kommunenummer) @Value(kommunenummer) AUTO @Value(arealformalkode) @Value(arealformalkode) AUTO @Value(planlagt_areal_m2) @Value(planlagt_areal_m2) AUTO @Value(ikrafttredelsesdato) @Value(ikrafttredelsesdato) AUTO @Value(kp_formal) @Value(kp_formal) AUTO @Value(rp_formal) @Value(rp_formal) AUTO
    MERGE_TYPE = Attributes Only
    PROCESS_DUPS = NO
    REJECT_NULL_MISSING_KEYS = No
    SUPPLIERS_FIRST = No
    MERGED -> AttributeManager_6
    UNMERGED_REQUESTOR -> AttributeManager_6
AttributeManager_6
    ATTR_TABLE:
      SET_TO bebygd_og_restareal_m2 = FME_CONDITIONAL:DEFAULT_VALUE'_FME_NO_OP_'BOOL_OP;OR;COMPOSITE_TEST;1 OR 2 OR 3;TEST bebygd_og_restareal_m2 ATTRIBUTE_VALUE_NULL _FME_BLANK_STRING_;TEST bebygd_og_restareal_m2 ATTRIBUTE_IS_EMPTY _FME_BLANK_STRING_;TEST bebygd_og_restareal_m2 ATTRIBUTE_IS_MISSING _FME_BLANK_STRING_'0'FME_NUM_CONDITIONS2___
      SET_TO test_areal_m2
      SET_TO planlagt_utbygd_areal_m2 = FME_CONDITIONAL:DEFAULT_VALUE'_FME_NO_OP_'BOOL_OP;OR;COMPOSITE_TEST;1 OR 2 OR 3;TEST planlagt_utbygd_areal_m2 ATTRIBUTE_VALUE_NULL _FME_BLANK_STRING_;TEST planlagt_utbygd_areal_m2 ATTRIBUTE_IS_EMPTY _FME_BLANK_STRING_;TEST planlagt_utbygd_areal_m2 ATTRIBUTE_IS_MISSING _FME_BLANK_STRING_'0'FME_NUM_CONDITIONS2___
    USER_EXPOSED_ATTRIBUTES = test_areal_m2
    -> AttributeRemover_4
AttributeRemover_4
    REMOVE_ATTRS = test_areal_m2
    -> AttributeCreator_2
    -> Junction_48
Note: Slå sammen areal attributter
FeatureMerger_7
    ATTR_ACCUM_MODE = Merge Supplier
    ATTR_CONFLICT_RES = Use Requestor
    IGNORE_NULLS = No
    JOIN_KEYS = @Value(planid) @Value(planid) AUTO @Value(kommunenummer) @Value(kommunenummer) AUTO @Value(arealformalkode) @Value(arealformalkode) AUTO @Value(planlagt_areal_m2) @Value(planlagt_areal_m2) AUTO @Value(ikrafttredelsesdato) @Value(ikrafttredelsesdato) AUTO @Value(kp_formal) @Value(kp_formal) AUTO @Value(rp_formal) @Value(rp_formal) AUTO
    MERGE_TYPE = Attributes Only
    PROCESS_DUPS = NO
    REJECT_NULL_MISSING_KEYS = No
    SUPPLIERS_FIRST = No
    MERGED -> AttributeManager_14
    UNMERGED_REQUESTOR -> AttributeManager_14
AttributeManager_14
    ATTR_TABLE:
      SET_TO bebygd_og_restareal_m2 = FME_CONDITIONAL:DEFAULT_VALUE'_FME_NO_OP_'BOOL_OP;OR;COMPOSITE_TEST;1 OR 2 OR 3;TEST bebygd_og_restareal_m2 ATTRIBUTE_VALUE_NULL _FME_BLANK_STRING_;TEST bebygd_og_restareal_m2 ATTRIBUTE_IS_EMPTY _FME_BLANK_STRING_;TEST bebygd_og_restareal_m2 ATTRIBUTE_IS_MISSING _FME_BLANK_STRING_'0'FME_NUM_CONDITIONS2___
      SET_TO test_areal_m2
      SET_TO planlagt_utbygd_areal_m2 = FME_CONDITIONAL:DEFAULT_VALUE'_FME_NO_OP_'BOOL_OP;OR;COMPOSITE_TEST;1 OR 2 OR 3;TEST planlagt_utbygd_areal_m2 ATTRIBUTE_VALUE_NULL _FME_BLANK_STRING_;TEST planlagt_utbygd_areal_m2 ATTRIBUTE_IS_EMPTY _FME_BLANK_STRING_;TEST planlagt_utbygd_areal_m2 ATTRIBUTE_IS_MISSING _FME_BLANK_STRING_'0'FME_NUM_CONDITIONS2___
      SET_TO ikrafttredelsesdato = FME_CONDITIONAL:DEFAULT_VALUE'_FME_NO_OP_'BOOL_OP;OR;COMPOSITE_TEST;1 OR 2 OR 3 OR 4;TEST @Value(ikrafttredelsesdato) = 000000;TEST ikrafttredelsesdato ATTRIBUTE_VALUE_NULL _FME_BLANK_STRING_;TEST ikrafttredelsesdato ATTRIBUTE_IS_EMPTY _FME_BLANK_STRING_;TEST ikrafttredelsesdato ATTRIBUTE_IS_MISSING _FME_BLANK_STRING_'18000101'FME_NUM_CONDITIONS2___
    USER_EXPOSED_ATTRIBUTES = test_areal_m2
    -> AttributeRemover_7
AttributeRemover_7
    REMOVE_ATTRS = test_areal_m2
    -> Junction_48
Aggregator_3
    ACCUM_ATTRS_NAME = Drop Incoming Attributes
    AGGREGATE_TYPE = Homogeneous Collection (If Possible)
    GROUP_BY = planid arealformalkode planlagt_areal_m2 ikrafttredelsesdato kommunenummer plankilde arealformalsgruppe arealformal plannmosaikkdato rp_formal kp_formal plan_overlapp omradenavn arealstatus plannavn plantype planbestemmelse planstatus lovreferanse kommune fylkesnummer fylke planlagt_utbygging
    MODE = Geometry - Assemble One Level
    SEP = ,
    AGGREGATE -> AttributeCreator_4
AttributeCreator_4
    ATTR_TABLE:
      SET_TO planlagt_utbygd_areal_m2 = FME_NULL_VALUE
      SET_TO bebygd_og_restareal_m2 = FME_NULL_VALUE
    -> Junction_48

Bookmark: WRITER
AttributeCreator_2
    ATTR_TABLE:
      SET_TO planlagt_utbygd_myr_m2 = FME_NULL_VALUE
      SET_TO planlagt_utbygd_skog_m2 = FME_NULL_VALUE
      SET_TO planlagt_utbygd_jordbruk_m2 = FME_NULL_VALUE
      SET_TO planlagt_utbygd_aapen_fastmark_m2 = FME_NULL_VALUE
      SET_TO planlagt_utbygd_annen_arealtype_m2 = FME_NULL_VALUE
      SET_TO planlagt_utbygd_i_faresone_m2 = FME_NULL_VALUE
      SET_TO planlagt_utbygd_kantsone_m2 = FME_NULL_VALUE
      SET_TO planlagt_utbygd_over_skoggrense_m2 = FME_NULL_VALUE
      SET_TO planlagt_utbygd_strandsone_m2 = FME_NULL_VALUE
      SET_TO planlagt_utbygd_villrein_m2 = FME_NULL_VALUE
      SET_TO planlagt_utbygd_iba_m2 = FME_NULL_VALUE
    -> AttributeManager_7
AttributeManager_7
    ATTR_TABLE = SET_TO ikrafttredelsesdato = FME_CONDITIONAL:DEFAULT_VALUE'18000101'BOOL_OP;OR;COMPOSITE_TEST;1 OR 2 OR 3 OR 4 OR 5;TEST ikrafttredelsesdato ATTRIBUTE_VALUE_NULL _FME_BLANK_STRING_;TEST ikrafttredelsesdato ATTRIBUTE_IS_EMPTY _FME_BLANK_STRING_;TEST ikrafttredelsesdato ATTRIBUTE_IS_MISSING _FME_BLANK_STRING_;TEST @Value(ikrafttredelsesdato) = 000000;TEST @Value(ikrafttredelsesdato) = 18000101'18000101'BOOL_OP;OR;COMPOSITE_TEST;1;TEST ikrafttredelsesdato ATTRIBUTE_HAS_A_VALUE _FME_BLANK_STRING_'@Value(ikrafttredelsesdato)'FME_NUM_CONDITIONS3___
    -> FeatureWriter_GeoPackage_Geometry [Table1]
AttributeManager_8
    ATTR_TABLE = SET_TO ikrafttredelsesdato = FME_CONDITIONAL:DEFAULT_VALUE'18000101'BOOL_OP;OR;COMPOSITE_TEST;1 OR 2 OR 3 OR 4 OR 5;TEST ikrafttredelsesdato ATTRIBUTE_VALUE_NULL _FME_BLANK_STRING_;TEST ikrafttredelsesdato ATTRIBUTE_IS_EMPTY _FME_BLANK_STRING_;TEST ikrafttredelsesdato ATTRIBUTE_IS_MISSING _FME_BLANK_STRING_;TEST @Value(ikrafttredelsesdato) = 000000;TEST @Value(ikrafttredelsesdato) = 18000101'18000101'BOOL_OP;OR;COMPOSITE_TEST;1;TEST ikrafttredelsesdato ATTRIBUTE_HAS_A_VALUE _FME_BLANK_STRING_'@Value(ikrafttredelsesdato)'FME_NUM_CONDITIONS3___
    -> FeatureWriter_GeoPackage_Geometry [Table102]
FeatureWriter_GeoPackage_Geometry
    DATASET = $(output_geopackage)
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DATASET_TEMPLATE = P:\412308_planlagt_utbygging_i_norge\planlagt-utbygging-beregning\data\input\planlagt-utbygging-template.gpkg
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = YES
    OGCGEOPACKAGE_TRANSACTION_SIZE = 5000
    OGCGEOPACKAGE_WRITE_NULLS = YES
    TOTAL_FEATURES_WRITTEN_ATTR = _total_features_written

Bookmark: Test Arealberegning Inspector
Note: Inspect PlanMosaikk
TestFilter_3
    DEFAULT_VALUE = <UNFILTERED>
    PASSED_TEST_GROUP_OUTPUT = FIRST
    TEST_LIST = "BOOL_OP,OR,COMPOSITE_TEST,""""""1"""""",TEST_CLAUSE,TEST @Value(planlagt_utbygging) = Ja",Planlagt Utbygging,"BOOL_OP,OR,COMPOSITE_TEST,""""""1"""""",TEST_CLAUSE,TEST @Value(planlagt_utbygging) = Nei",Bebygd og Restareal,"BOOL_OP,OR,COMPOSITE_TEST,""""""1"""""",TEST_CLAUSE,TEST @Value(planlagt_utbygging) = Arealformål ekskludert fra beregning",ekskludert fra beregning
    Planlagt Utbygging -> Inspector_2
    Bebygd og Restareal -> Inspector_2
    ekskludert fra beregning -> Inspector_2
Inspector_2

FME custom transformer LargestInnerCircleCreator
Creats the largest circle entierly within area/polygon features. The calculation is approximate.

Parameters:
- AccuracyLevel = 30   # High,100%Very Low,10 Select the level of accuracy (will effect performance significantly)

Area (input)
    -> GeometryFilter
GeometryFilter
    BREAK_AGG = No
    GEOM_PORT_NAMES = Area Ellipse
    AREA -> Counter
    ELLIPSE -> Counter
    <UNFILTERED> -> InvalidGeometry (output)
Note: Create an ID for each polygon
Counter
    CNT_ATTR = _count
    DOMAIN = counter
    SCOPE = Global
    START = 0
    -> 2DGridAccumulator
    -> Clipper [CLIPPER]
    -> NeighborFinder [CANDIDATE]
    -> NeighborFinder_2 [CANDIDATE]
    -> Area (output)
Note: Extract Coordinates of circle centepoints
CoordinateExtractor
    LIST_NAME = _indices
    MODE = All Coordinates
    -> 2DEllipseReplacer
Note: Create circles
2DEllipseReplacer
    PRIMAXIS = @Value(_distance)
    ROT = 0
    SECAXIS = @Value(_distance)
    XVALATTR = @Value(_indices{0}.x)
    YVALATTR = @Value(_indices{0}.y)
    ELLIPSE -> AttributeManager
Note: CleanUp
AttributeManager
    ATTR_TABLE:
      REMOVE _count
      REMOVE _column
      REMOVE _row
      RENAME_SET_VALUE _distance > _radius
      REMOVE _angle
      REMOVE _candidate_angle
      REMOVE _candidate_label_angle
      REMOVE _closest_candidate_x
      REMOVE _closest_candidate_y
      REMOVE _closest_base_x
      REMOVE _closest_base_y
      REMOVE _indices{}.z
      SET_TO _centre_x = @Value(_indices{0}.x)
      SET_TO _centre_y = @Value(_indices{0}.y)
    -> AttributeRemover
AttributeRemover
    LIST_ATTRS = _indices{}.x _indices{}.y
    -> Circles (output)
Circles (output)
Area (output)
InvalidGeometry (output)

Bookmark: Break Polygon into parts (1)
Note: Create Grid over each polygon
2DGridAccumulator
    COL_ATTR = _column
    GRID_TYPE = Polygons
    GROUP_BY = _count
    ROW_ATTR = _row
    SIZE_TYPE = Number of Cells
    STARTINGCORNER = Lower Left
    XCOUNT = $(AccuracyLevel)
    YCOUNT = $(AccuracyLevel)
    GRID -> Clipper [CLIPPEE]
Note: Clip Grid so that only features in each polygon remain
Clipper
    BOUNDARY_CASES = Treat as Inside
    CLIPPED_ATTR = _clipped
    CLIP_TYPE = Multiple Clippers
    CONNECT_Z_MODE = First Wins
    CREATE_AGGREGATES = Yes
    GROUP_BY = _count
    LINES_AS_SEGMENTS = No
    PRESERVE_CLIPPEE_EXTENTS = No
    INSIDE -> NeighborFinder [BASE]

Bookmark: Find Centre Grid Unit (2)
NeighborFinder
    ATTR_ACCUM_MODE = Merge Candidate
    ATTR_CONFLICT_RES = Use Base
    CANDIDATES_FIRST = No
    GROUP_BY = _count
    INSERT_VERTEX = No
    K = 1
    MODE = Bases and Candidates
    TREAT_POLYGON_AS = Lines
    MATCHED -> Sorter
Sorter
    SORT_PARM = _count NUMERIC ASCENDING _distance NUMERIC DESCENDING
    SORTED -> Sampler
Sampler
    GROUP_BY = _count
    RATE = 1
    SAMPLE_MODE = No
    SAMPLE_TYPE_LONG = First N Features
    SAMPLED -> 2DGridAccumulator_2

Bookmark: Repeat Stepts 2 and 3 to increase accuracy
2DGridAccumulator_2
    COL_ATTR = _column
    GRID_TYPE = Points (Centers)
    GROUP_BY = _count
    ROW_ATTR = _row
    SIZE_TYPE = Number of Cells
    STARTINGCORNER = Lower Left
    XCOUNT = 25
    YCOUNT = 25
    GRID -> NeighborFinder_2 [BASE]
NeighborFinder_2
    ATTR_ACCUM_MODE = Merge Candidate
    ATTR_CONFLICT_RES = Use Base
    CANDIDATES_FIRST = No
    GROUP_BY = _count
    INSERT_VERTEX = No
    K = 1
    MODE = Bases and Candidates
    TREAT_POLYGON_AS = Lines
    MATCHED -> Sorter_2
Sorter_2
    SORT_PARM = _count NUMERIC ASCENDING _distance NUMERIC DESCENDING
    SORTED -> Sampler_2
Sampler_2
    GROUP_BY = _count
    RATE = 1
    SAMPLE_MODE = No
    SAMPLE_TYPE_LONG = First N Features
    SAMPLED -> CoordinateExtractor

FME custom transformer Planlagt_utbygd_areal_beregning

Parameters:
- Kommune = 4201
- OUTPUT = FME_DISCLOSURE_OPEN   # OutputSti Output
- OutputSti = C:\Temp\Arealregnskap   # Velg sti for output
- AREALFORMAL = @Value(arealformal)   # arealformal
- AREALFORMALKODE = @Value(arealformalkode)   # arealformalkode
- AREALFORMALSGRUPPE_2 = @Value(arealformalsgruppe)   # arealformalsgruppe
- AREALSTATUS = @Value(arealstatus)   # arealstatus
- AREALTYPE = @Value(arealtype)   # arealtype
- FYLKE = @Value(fylke)   # fylke
- FYLKESNUMMER = @Value(fylkesnummer)   # fylkesnummer
- HOVEDKLASSE = @Value(hovedklasse)   # hovedklasse
- IKRAFTTREDELSESDATO = @Value(ikrafttredelsesdato)   # ikrafttredelsesdato
- KOMMUNE = @Value(kommune)   # kommune
- KOMMUNENUMMER = @Value(kommunenummer)   # kommunenummer
- KP_FORMAL = @Value(kp_formal)   # Kp Formal
- LOVREFERANSE = @Value(lovreferanse)   # lovreferanse
- OMRADENAVN = @Value(omradenavn)   # omradenavn
- PLAN_OVERLAPP = @Value(plan_overlapp)   # Plan Overlapp
- PLANBESTEMMELSE = @Value(planbestemmelse)   # planbestemmelse
- PLANID = @Value(planid)   # planid
- PLANKILDE = @Value(plankilde)   # plankilde
- PLANLAGT_AREAL_M2 = @Value(planlagt_areal_m2)   # Planlagt Areal M2
- PLANNAVN = @Value(plannavn)   # plannavn
- PLANNMOSAIKKDATO = @Value(plannmosaikkdato)   # plannmosaikkdato
- PLANSTATUS = @Value(planstatus)   # planstatus
- PLANTYPE = @Value(plantype)   # plantype
- RP_FORMAL = @Value(rp_formal)   # Rp Formal
- PARAMETER_2 =   # Diverse innstillinger
- rp_exclude = 200,210,220,230,299,392,400,410,420,421,430,450,459,460,461,463,469,540,550,590,600,611,613,614,619,622,626,631,645,646,650,651,652,660,661,662,663,680,681,699,780,999,1587,1588,3000,3001,3002,3020,3030,3031,3040,3041,3050,3060,3061,3100,3110,3800,3900,4000,4001,4010,4020,4800,4900,5000,5001,5100,5110,5111,5112,5113,5114,5115,5120,5130,5140,5200,5210,5220,5230,5300,5400,5500,5600,5900,6000,6001,6100,6110,6120,6130,6200,6210,6211,6220,6230,6240,6300,6310,6320,6330,6400,6410,6500,6600,6610,6620,6700,6710,6720,6730,6740,6760,6770,6800,6900   # Reguleringsplan arealformål som skal ekskluderes
- arealformal_exclude = 3002,3020,3030,3040,3050,3100,3800,4001,4010,4020,4800,5100,5200,5210,5220,5230,6001,6100,6110,6120,6130,6200,6220,6230,6300,6400,6500,6600,6700,6800,9999   # Arealformål som skal ekskluderes

Fkb_bygning (input)
    -> Bufferer
Fkb_tiltak (input)
    -> Bufferer
Note: 15 m buffer
Bufferer
    ANGLE = 22.5
    CAP_STYLE = Arc
    CORNER_STYLE = Arc
    MODE = AREA
    OFFSET = 15
    OFFSET_UNITS = NONE
    PRECISION = APPROX
    BUFFERED -> Clipper [CLIPPER]
Fkb_veg (input)
    -> Bufferer_2
Note: 5 m buffer
Bufferer_2
    ANGLE = 22.5
    CAP_STYLE = Arc
    CORNER_STYLE = Arc
    MODE = AREA
    OFFSET = 5
    OFFSET_UNITS = NONE
    PRECISION = APPROX
    BUFFERED -> Junction_7
Note: Til Clipper 4
Junction_7
    -> Junction_8
AR5 (input)
    -> AttributeKeeper_3
AttributeKeeper_3
    CREATE_BULK_MODE_FEATURES = NO
    KEEP_ATTRS = arealtype
    -> AreaCalculator_2
AreaCalculator_2
    AREA_ATTR = _area
    AREA_TYPE = Plane Area
    MULT = 1
    -> Tester_4
Note: Utelater vann større enn 500 kvm fra beregning planreserve
Tester_4
    BOOL_OP = COMPOSITE
    COMPOSITE_TEST = 1 AND 2
    TEST_CLAUSE:
      TEST @Value(arealtype) = 81
      TEST @Value(_area) > 500
    TEST_MODE = TEST
    PASSED -> Clipper_3 [CLIPPER]
SSB_Arealbruk (input)
    -> Clipper_3 [CLIPPER]
Ekskluderingsflate (input)
    -> Clipper_3 [CLIPPER]
PLAN (input)
    -> AttributeKeeper_2
AttributeKeeper_2
    CREATE_BULK_MODE_FEATURES = NO
    KEEP_ATTRS = arealformal,arealformalkode,arealformalsgruppe,arealstatus,fylke,fylkesnummer,hovedklasse,ikrafttredelsesdato,kommune,kommunenummer,kp_formal,lovreferanse,omradenavn,plan_overlapp,planbestemmelse,planid,plankilde,planlagt_areal_m2,plannavn,plannmosaikkdato,planstatus,plantype,rp_formal
    -> Tester_8
Note: Beholde planer med byggeformål. Se arealformal_exclude liste
Tester_8
    BOOL_OP = OR
    TEST_CLAUSE = TEST @Value(arealformalkode) IN $(arealformal_exclude)
    TEST_MODE = TEST
    PASSED -> Junction_4
    FAILED -> Clipper_3 [CANDIDATE]
    FAILED -> Junction
Note: PLAN - SSB / outside = planreserve
Clipper_3
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    OUTSIDE -> Deaggregator_3
Note: multipolygon > polygon
Deaggregator_3
    EXPLODE_INSTANCES = No
    GEOM_NAME_FIELD = _geometry_name
    LIST_ATTR_MODE_LOOKUP = LEAN
    MODE = Flatten All Levels
    SPLIT_COMPOSITES = No
    DEAGGREGATED -> Dissolver
Dissolver
    ACCUM_INPUT_ATTRS = Use Attributes From One Feature
    CLEANING_TOLERANCE = Automatic
    CONNECT_Z_MODE = First Wins
    DEAGGREGATE_INPUT = Yes
    GROUP_BY = arealformalkode plankilde arealformal arealformalsgruppe arealstatus fylke fylkesnummer hovedklasse ikrafttredelsesdato kommune kommunenummer kp_formal lovreferanse omradenavn plan_overlapp planbestemmelse planid planlagt_areal_m2 plannavn plannmosaikkdato planstatus plantype rp_formal
    AREA -> Tester
Note: Bolig, fritidsbolig, næering
Tester
    BOOL_OP = OR
    TEST_CLAUSE:
      TEST @Value(arealformalkode) = 1001
      TEST @Value(arealformalkode) = 1110
      TEST @Value(arealformalkode) = 1120
      TEST @Value(arealformalkode) = 1130
      TEST @Value(arealformalkode) = 1150
      TEST @Value(arealformalkode) = 1160
      TEST @Value(arealformalkode) = 1300
      TEST @Value(arealformalkode) = 1500
      TEST @Value(arealformalkode) = 1800
      TEST @Value(arealformalkode) = 1140
      TEST @Value(arealformalkode) = 4030
    TEST_MODE = TEST
    PASSED -> Clipper [CANDIDATE]
    FAILED -> Tester_12
Note: PLAN-SSB-FKB bygg / outside = planreserve
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator
Note: multipolygon > polygon
Note: Fritidsbolig og bolig, næring / Planlagt Utbygging = PLAN - SSB - FKB bygg (15m buffer) - "sirkeltesten" / Arealfromalkode = 1001 1110 1120 1130 1140 1150 1160 1300 1500 1800 4030)
Deaggregator
    EXPLODE_INSTANCES = No
    GEOM_NAME_FIELD = _geometry_name
    LIST_ATTR_MODE_LOOKUP = LEAN
    MODE = Flatten All Levels
    SPLIT_COMPOSITES = No
    DEAGGREGATED -> Dissolver_3
Note: Samferdsel: / Planlagt Utbygging = PLAN - SSB - AR5 (vann > 500m2) - FKB veg (buffer5m) / Arealformalkode = 2001, 2010, 2020, 2030, 2050, 2060, 2070, 2080, 2100, 2800
Dissolver_3
    ACCUM_INPUT_ATTRS = Use Attributes From One Feature
    CLEANING_TOLERANCE = Automatic
    CONNECT_Z_MODE = First Wins
    DEAGGREGATE_INPUT = Yes
    GROUP_BY = arealformalkode plankilde arealformal arealformalsgruppe arealstatus fylke fylkesnummer hovedklasse ikrafttredelsesdato kommune kommunenummer kp_formal lovreferanse omradenavn plan_overlapp planbestemmelse planid planlagt_areal_m2 plannavn plannmosaikkdato planstatus plantype rp_formal
    AREA -> AreaCalculator
Note: Samferdsel
Tester_12
    BOOL_OP = OR
    TEST_CLAUSE = TEST @Value(arealformalsgruppe) = 11 Samferdselsanlegg
    TEST_MODE = TEST
    PASSED -> Clipper_4 [CANDIDATE]
    FAILED -> Junction_6
AttributeCreator
    ATTR_TABLE = SET_TO pu_code = 1
    -> Planreserve
    -> AttributeKeeper
AttributeKeeper
    CREATE_BULK_MODE_FEATURES = NO
    KEEP_ATTRS = pu_code
    -> Clipper_2 [CLIPPER]
Planreserve: Inspector
Note: Til Clipper 2
Junction
    -> Junction_5
Note: Plandata
Junction_5
    -> Clipper_2 [CANDIDATE]
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_4
    OUTSIDE -> Deaggregator_4
Note: multipolygon > polygon
Deaggregator_4
    EXPLODE_INSTANCES = No
    GEOM_NAME_FIELD = _geometry_name
    LIST_ATTR_MODE_LOOKUP = LEAN
    MODE = Flatten All Levels
    SPLIT_COMPOSITES = No
    DEAGGREGATED -> Dissolver_4
Dissolver_4
    ACCUM_INPUT_ATTRS = Use Attributes From One Feature
    CLEANING_TOLERANCE = Automatic
    CONNECT_Z_MODE = First Wins
    DEAGGREGATE_INPUT = Yes
    GROUP_BY = arealformalkode plankilde arealformal arealformalsgruppe arealstatus fylke fylkesnummer hovedklasse ikrafttredelsesdato kommune kommunenummer kp_formal lovreferanse omradenavn plan_overlapp planbestemmelse planid planlagt_areal_m2 plannavn plannmosaikkdato planstatus plantype rp_formal pu_code
    AREA -> AttributeCreator_4
AttributeCreator_4
    ATTR_TABLE = SET_TO pu_code = FME_CONDITIONAL:DEFAULT_VALUE'_FME_NO_OP_'BOOL_OP;OR;COMPOSITE_TEST;1;TEST @Value(pu_code) != 1'0'FME_NUM_CONDITIONS2___
    -> AttributeManager
AttributeManager
    ATTR_TABLE:
      REMOVE hovedklasse
      REMOVE _clipped
      REMOVE _geometry_name
    USER_EXPOSED_ATTRIBUTES = planlagt_utbygging
    -> Junction_3
Note: Annen: / Planlagt Utbygging = PLAN - SSB - AR5 (vann > 500m2) / Arealformalkode = 1170, 1200,1400, 1600,1700,2040,2044,4020,6200,6230,6400
Junction_4
    -> AttributeCreator_2
AttributeCreator_2
    ATTR_TABLE = SET_TO pu_code = 9999
    -> Junction_3
Junction_3
    -> Output (output)
Output (output)

Bookmark: Samferdsel:
Note: FKB Veg Buffer
Junction_8
    -> Clipper_4 [CLIPPER]
Note: PLAN - SSB- FKB vegg = planreserve
Clipper_4
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator_2
Note: multipolygon > polygon
Deaggregator_2
    EXPLODE_INSTANCES = No
    GEOM_NAME_FIELD = _geometry_name
    LIST_ATTR_MODE_LOOKUP = LEAN
    MODE = Flatten All Levels
    SPLIT_COMPOSITES = No
    DEAGGREGATED -> Dissolver_2
Dissolver_2
    ACCUM_INPUT_ATTRS = Use Attributes From One Feature
    CLEANING_TOLERANCE = Automatic
    CONNECT_Z_MODE = First Wins
    DEAGGREGATE_INPUT = Yes
    GROUP_BY = arealformalkode plankilde arealformal arealformalsgruppe arealstatus fylke fylkesnummer hovedklasse ikrafttredelsesdato kommune kommunenummer kp_formal lovreferanse omradenavn plan_overlapp planbestemmelse planid planlagt_areal_m2 plannavn plannmosaikkdato planstatus plantype rp_formal
    AREA -> AreaCalculator_3
AreaCalculator_3
    AREA_ATTR = _area
    AREA_TYPE = Plane Area
    MULT = 1
    -> Tester_9
Tester_9
    BOOL_OP = OR
    TEST_CLAUSE = TEST @Value(_area) > 250
    TEST_MODE = TEST
    PASSED -> AttributeCreator

Bookmark: Beregning av Roundness
AreaCalculator
    AREA_ATTR = _area
    AREA_TYPE = Plane Area
    MULT = 1
    -> LengthCalculator
LengthCalculator
    DIM = 2
    LEN_ATTR = _length
    MULT = 1
    -> AttributeCreator_3
Note: roundness=length/area / area-to-perimeter ratio / roundness = 4*pi/convex perimeter^2 / 1 = circular object, <1 object departs from circularity.
AttributeCreator_3
    ATTR_TABLE = SET_TO _roundness = @Evaluate(@Value(_length)/@Value(_area))
    -> Tester_10

Bookmark: Siler vekk objekter for bedre ytelse.
Note: Utelater flater for næring++ under 1 dekar, ikke plass til næring utbygging
Tester_10
    BOOL_OP = COMPOSITE
    COMPOSITE_TEST = 1 AND 2
    TEST_CLAUSE:
      TEST @Value(arealformalsgruppe) IN 03 Tjenesteyting,04 Handel,06 Næringsvirksomhet,08 Kombinerte formål,10 Andre formål,13 Forsvaret
      TEST @Value(_area) < 1000
    TEST_MODE = TEST
    FAILED -> Tester_5
Note: filtrerer ut områder > 250 m2
Tester_5
    BOOL_OP = OR
    TEST_CLAUSE = TEST @Value(_area) > 250
    TEST_MODE = TEST
    PASSED -> Tester_6
Note: Filtrer på roundness og størrelse.
Tester_6
    BOOL_OP = COMPOSITE
    COMPOSITE_TEST = 1 AND 2
    TEST_CLAUSE:
      TEST @Value(_roundness) > 0.25
      TEST @Value(_area) < 1000
    TEST_MODE = TEST
    FAILED -> Tester_11
Note: Filtrer på roundness og størrelse: for stort rest areal. Med i planreserve beregning
Tester_11
    BOOL_OP = COMPOSITE
    COMPOSITE_TEST = 1 AND 2
    TEST_CLAUSE:
      TEST @Value(_roundness) < 0.15
      TEST @Value(_area) > 1000
    TEST_MODE = TEST
    PASSED -> Junction_2
    FAILED -> LargestInnerCircleCreator_2 [Area]

Bookmark: Fritidsbolig og bolig, næring
LargestInnerCircleCreator_2
    AccuracyLevel = 20
    Area -> SpatialFilter [Candidate]
    Circles -> Tester_2
Tester_2
    BOOL_OP = OR
    TEST_CLAUSE = TEST @Value(_radius) > 10
    TEST_MODE = TEST
    PASSED -> SpatialFilter [Filter]
Note: Area WITHIN Cirkel
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> Junction_2
    FAILED -> Inspector
Junction_2
    -> AttributeCreator
Note: Ubebyggbar areal (to small to build a building) / basert på SSB 20 m
Inspector

Bookmark: Annen:
Junction_6
    -> AreaCalculator_4
AreaCalculator_4
    AREA_ATTR = _area
    AREA_TYPE = Plane Area
    MULT = 1
    -> Tester_3
Tester_3
    BOOL_OP = OR
    TEST_CLAUSE = TEST @Value(_area) > 150
    TEST_MODE = TEST
    PASSED -> Junction_9
Junction_9
    -> AttributeCreator
