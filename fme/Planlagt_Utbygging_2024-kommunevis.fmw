FME workspace Planlagt_Utbygging_2024-kommunevis.fmw

Parameters:
- Kommune = 4219
- PARAMETER_2 = FME_DISCLOSURE_OPEN   # Diverse innstillinger
- KommuneplanOverstyring = 0   # LNFR i kommuneplan gjelder foran reguleringsplan (Ja/Nei) (NB! Fjerner veiformål)
- KpExclude = 200,210,330,410,420,470,490,499,500,510,520,530,531,532,540,541,542,590,5000,5001,5100,6000,6001,6100,6110,6120,6130,6200,6300,6600,6700,6800
- FormalTilBeregning = 1001,1110,1120,1130,1140,1150,1160,1200,1300,1400,1800,2010,2080
- OUTPUT = FME_DISCLOSURE_OPEN   # Output
- OutputSti = Q:\_TEMP_FILUTVEKSLING\Andreas   # Velg sti for output
- PARAMETER =   # Input - datakilder
- PARAMETER_5 =   # Plandata
- KP_SOSI = Q:\PLAN\KOMMUNEPLAN\Kommuneplaner\$(Kommune)*.sos   # Velg kommuneplan (SOSI)
- KDP_SOSI = Q:\PLAN\KOMMUNEPLAN\Kommunedelplaner\$(Kommune)*.sos   # Velg kommunedelplan (SOSI)
- RP_FGDB = $(FME_MF_DIR)Plan_4219_Evje_og_Hornnes_25832_Reguleringsplaner_FGDB\Plan_4219_Evje_og_Hornnes_25832_Reguleringsplaner_FGDB\Plan_4219_Evje_og_Hornnes_25832_Reguleringsplaner_vn2_FGDB.gdb   # Velg reguleringsplanbase (FGDB)
- PARAMETER_3 =   # FKB-data
- TILTAK_FGDB = Q:\BASISDATA\_FKB\FGDB/*FKB-Tiltak*\*$(Kommune)*FKB-Tiltak*.gdb   # FKB Tiltak (FGDB)
- BYGNING_FGDB = Q:\BASISDATA\_FKB\FGDB\*FKB-Bygning*\*$(Kommune)*FKB-Bygning*.gdb   # FKB Bygning (FGDB)
- VEG_FGDB = Q:\BASISDATA\_FKB\FGDB\*FKB-Veg*\*$(Kommune)*FKB-Veg*.gdb   # FKB Veg (FGDB)
- AR5_FGDB = Q:\BASISDATA\_FKB\FGDB\*FKB-AR5*\*$(Kommune)*FKB-AR5*.gdb   # FKB AR5 (FGDB)
- PARAMETER_4 =   # SSBAREALBRUK_FGDB Øvrige data
- SSBAREALBRUK_FGDB = C:\Users\afk03032\Downloads\*Arealbruk2023_FGDB\*$(Kommune)*Arealbruk2023_FGDB.gdb   # SSB Arealbruk (FGDB)
- PARAMETER_6 =   # Excel
- SourceDataset_XLSXR_5 = Q:\ANALYSE\Arealregnskap\Reguleringsplaner\Reguleringsplaner_Ikke_Med.xlsx   # Ekskluderte reguleringsplaner (Excel)

Readers:
- XLSXR_2: XLSXR from $(SourceDataset_XLSXR_5)

Writers:
- FILEGDB_6: FILEGDB to $(OutputSti)/AR5_SSB.gdb

Initiator: Creator
    GEOMTYPE = Geometry Object
    NUM = 1
    CREATED -> AttributeCreator_14
    CREATED -> AttributeCreator_15
AttributeCreator_15
    ATTR_TABLE:
      SET_TO TILTAK_URL (varchar(200)) = $(TILTAK_FGDB)
      SET_TO BYGNING_URL (varchar(200)) = $(BYGNING_FGDB)
      SET_TO VEG_URL (varchar(200)) = $(VEG_FGDB)
      SET_TO AR5_URL (varchar(200)) = $(AR5_FGDB)
      SET_TO SSBAREALBRUK_URL (varchar(200)) = $(SSBAREALBRUK_FGDB)
    -> LesGrunndata
LesGrunndata
    AR5_URL = @Value(AR5_URL)
    BYGNING_URL = @Value(BYGNING_URL)
    SSBAREALBRUK_URL = @Value(SSBAREALBRUK_URL)
    TILTAK_URL = @Value(TILTAK_URL)
    VEG_URL = @Value(VEG_URL)
    FKB_Tiltak -> Planreserveberegning [Fkb_tiltak]
    FKB_Veg -> Planreserveberegning [Fkb_veg]
    FKB_Bygning -> Planreserveberegning [Fkb_bygning]
    FKB_AR5 -> Planreserveberegning [AR5]
    SSB_Arealbruk -> Planreserveberegning [SSB]
AttributeCreator_14
    ATTR_TABLE:
      SET_TO RP_URL (varchar(200)) = $(RP_FGDB)
      SET_TO KP_URL (varchar(200)) = $(KP_SOSI)
      SET_TO KDP_URL (varchar(200)) = $(KDP_SOSI)
    -> LesPlandata
LesPlandata
    DEST = ETRS89.UTM-33N
    KDP_URL = @Value(KDP_URL)
    KP_URL = @Value(KP_URL)
    Kommune = 4221
    RP_URL = @Value(RP_URL)
    Kommuneplan -> AttributeValueMapper_6
    Reguleringsplan -> AttributeValueMapper_10
    RpOmråde -> Junction_4
Junction_4
    -> FeatureMerger [SUPPLIER]
FeatureMerger
    ATTR_ACCUM_MODE = Merge Supplier
    ATTR_CONFLICT_RES = Use Requestor
    IGNORE_NULLS = No
    JOIN_KEYS = @Value(Planid) @Value(planidentifikasjon) AUTO @Value(kommunenummer) @Value(kommunenummer) AUTO
    MERGE_TYPE = Attributes Only
    PROCESS_DUPS = NO
    REJECT_NULL_MISSING_KEYS = No
    SUPPLIERS_FIRST = No
    MERGED -> AreaOnAreaOverlayer_4 [AREA]
    MERGED -> Clipper [CANDIDATE]
    UNMERGED_REQUESTOR -> Clipper [CANDIDATE]
AreaOnAreaOverlayer_4
    ACCUM_ATTRS_NAME = Merge Incoming Attributes
    CLEANING_TOLERANCE = Automatic
    CONNECT_Z_MODE = First Wins
    DEAGGREGATE_INPUT = Yes
    LIST_ATTRS_TO_INCLUDE = Arealformålkode kommunenummer Planid planidentifikasjon Plankilde RpFormål Ikrafttredelsesdato Plannavn
    LIST_NAME = attri
    OVC_ATTR = _overlaps
    AREA -> UUIDGenerator_2
UUIDGenerator_2
    UUID_ATTR = _uuid
    UUID_FORMAT = UUID_ONLY
    -> ListExploder
ListExploder
    ATTR_ACCUM_MODE = Prefix List Attributes
    INCOMING_PREFIX = _attri_
    INDEX_ATTR = _element_index
    LIST_ATTR = attri{}
    ELEMENTS -> Tester_16
Tester_16
    BOOL_OP = OR
    TEST_CLAUSE = TEST @Value(_overlaps) > 1
    TEST_MODE = TEST
    PASSED -> BulkAttributeRemover_3
BulkAttributeRemover_3
    ATTR_EXP = \b[^_]\w+
    -> Sorter
Sorter
    SORT_PARM = _attri_Ikrafttredelsesdato NUMERIC DESCENDING
    SORTED -> Sampler
Sampler
    GROUP_BY = _uuid
    RATE = 1
    SAMPLE_MODE = No
    SAMPLE_TYPE_LONG = First N Features
    SAMPLED -> AttributeRemover_2
AttributeRemover_2
    REMOVE_ATTRS = _area,_element_index,_overlaps,_attri_Kobling,_attri_planidentifikasjon,_attri__uuid,_uuid
    -> BulkAttributeRenamer
BulkAttributeRenamer
    ATTRCHOICE = All Attributes
    CASE_DISP = YES
    MODE_CHOICE = RENAME
    PATTERN_ACTION_DISP = REMOVEPREFIX
    REPLACE_STR = _attri_
    -> Dissolver_4
Dissolver_4
    ACCUM_INPUT_ATTRS = Use Attributes From One Feature
    CLEANING_TOLERANCE = Automatic
    CONNECT_Z_MODE = First Wins
    DEAGGREGATE_INPUT = Yes
    GROUP_BY = Arealformålkode kommunenummer Planid Plankilde RpFormål Ikrafttredelsesdato Plannavn
    AREA -> Clipper [CLIPPER]
    AREA -> Junction_22
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Junction_22
Junction_22
    -> AttributeKeeper_18
AttributeKeeper_18
    CREATE_BULK_MODE_FEATURES = NO
    KEEP_ATTRS = Arealformålkode,Planid,Plankilde,RpFormål,Ikrafttredelsesdato,Plannavn
    -> FeatureMerger_3 [REQUESTOR]
Junction_3
    -> FeatureMerger_3 [SUPPLIER]

Bookmark: Kommuneplan - Klargjøring før kobling med øvrige plandata
AttributeValueMapper_6
    LUT = 100,1001,1000,1001,1001,1001,101,1110,102,1110,110,1110,1110,1110,1120,1120,1130,1130,1140,1140,1150,1150,1160,1160,1170,1170,120,1130,1200,1200,130,1300,1300,1300,131,1150,132,1300,133,1300,134,1300,140,1120,1400,1400,150,1160,1500,1500,155,1160,160,1160,1600,1600,161,1700,162,1160,163,1160,170,3040,1700,1700,171,1400,172,3050,173,3030,1800,1800,190,1500,191,1500,200,5100,2000,2001,2001,2001,2010,2010,2020,2020,2030,2030,2040,2040,2044,2044,2050,2050,2060,2060,2070,2070,2080,2080,210,5100,2100,2100,220,5200,221,5210,222,5230,223,5220,2800,2800,300,1200,3000,3002,3001,3002,3002,3002,3020,3020,3030,3030,3040,3040,3050,3050,310,1200,3100,3100,320,1200,330,5100,3800,3800,400,1001,4000,4001,4001,4001,4010,4010,4020,4020,4030,4030,410,5100,420,5100,460,4001,470,1500,4800,4800,490,5100,499,5100,500,6001,5000,5100,5001,5100,510,6500,5100,5100,520,6700,5200,5220,521,6230,5210,5210,522,6700,5220,5220,5230,5230,530,6001,531,6100,532,6300,533,6400,540,6001,541,6700,542,6600,590,6800,600,2001,6000,6001,6001,6001,610,2010,6100,6100,6110,6110,6120,6120,6130,6130,620,2080,6200,6200,6220,6220,6230,6230,630,2001,6300,6300,631,2001,632,2050,640,2070,6400,6400,641,2070,650,2020,6500,6500,660,2020,6600,6600,670,2030,6700,6700,680,2040,6800,6800
    MAPPING_DIRECTION = FORWARD
    SRC = KpFormål
    VAL_ATTR = Arealformålkode
    -> AttributeCreator_3
AttributeCreator_3
    ATTR_TABLE = SET_TO Arealstatus = FME_CONDITIONAL:DEFAULT_VALUE'1'BOOL_OP;OR;COMPOSITE_TEST;1;TEST @Value(Arealstatus) = 2'2'FME_NUM_CONDITIONS2___
    -> AttributeKeeper_9
AttributeKeeper_9
    CREATE_BULK_MODE_FEATURES = NO
    KEEP_ATTRS = Plankilde,Områdenavn,Arealstatus,KpFormål,Arealformålkode
    -> Tester_6
Note: Ekskluderer enkelte arealformål (blir til LNFR)
Tester_6
    BOOL_OP = OR
    TEST_CLAUSE = TEST @Value(Arealformålkode) IN $(KpExclude)
    TEST_MODE = TEST
    FAILED -> Junction_2
Junction_2
    -> AttributeRenamer_7

Bookmark: Union mellom Kommuneplan og reguleringsplan
AttributeRenamer_7
    ATTR_TABLE:
      RENAME_SET_DEFAULT Arealformålkode > KplArealformålkode
      RENAME_SET_DEFAULT Plankilde > KplPlankilde
    MISSING_INPUT_ATTRS = REMOVE
    -> AreaOnAreaOverlayer_2 [AREA]
AreaOnAreaOverlayer_2
    ACCUM_ATTRS_NAME = Merge Incoming Attributes
    CLEANING_TOLERANCE = Automatic
    CONNECT_Z_MODE = First Wins
    DEAGGREGATE_INPUT = Yes
    AREA -> Tester_5
Tester_5
    BOOL_OP = OR
    TEST_CLAUSE = NUM_TEST Arealformålkode ATTRIBUTE_IS_MISSING ""
    TEST_MODE = NUM_TEST
    PASSED -> BulkAttributeRenamer_3
    FAILED -> AttributeCreator_9
AttributeCreator_9
    ATTR_TABLE = SET_TO Arealstatus = FME_CONDITIONAL:DEFAULT_VALUE'@Value(Arealstatus)'BOOL_OP;OR;COMPOSITE_TEST;1;TEST Arealstatus ATTRIBUTE_IS_MISSING _FME_BLANK_STRING_'1'FME_NUM_CONDITIONS2___
    -> Tester_9
Note: Kommuneplaner med arealstatus=2 har forrang foran eldre regplaner (pre pbl 2008)
Tester_9
    BOOL_OP = COMPOSITE
    COMPOSITE_TEST = 1 AND 2
    TEST_CLAUSE:
      TEST @Value(Plankilde) = RbFormålOmråde
      TEST @Value(Arealstatus) = 2
    TEST_MODE = TEST
    PASSED -> AttributeKeeper_11
    FAILED -> AttributeKeeper
AttributeKeeper_11
    CREATE_BULK_MODE_FEATURES = NO
    KEEP_ATTRS = KplPlankilde,Arealstatus,Områdenavn,Planid,KpFormål,RpFormål,KplArealformålkode
    -> BulkAttributeRenamer_3
BulkAttributeRenamer_3
    ATTRCHOICE = All Attributes
    CASE_DISP = YES
    MODE_CHOICE = RENAME
    PATTERN_ACTION_DISP = REMOVEPREFIX
    REPLACE_STR = Kpl
    -> Junction_10
AttributeKeeper
    CREATE_BULK_MODE_FEATURES = NO
    KEEP_ATTRS = Plankilde,Planid,Arealstatus,Områdenavn,KpFormål,RpFormål,Arealformålkode,Ikrafttredelsesdato,Plannavn
    -> Junction_10
Junction_10
    -> AttributeValueMapper_7
Note: Legge til areaformålsgruppe (generalisert)
AttributeValueMapper_7
    LUT = 1001,01 Bolig eller sentrumsformål,1110,01 Bolig eller sentrumsformål,1120,02 Fritidsbebyggelse,1130,01 Bolig eller sentrumsformål,1140,04 Handel,1150,04 Handel,1160,03 Tjenesteyting,1170,05 Turistformål,1200,07 Råstoffutvinning,1300,06 Næringsvirksomhet,1400,09 Idrettsanlegg,1500,10 Andre formål,1600,10 Andre formål,1700,10 Andre formål,1800,08 Kombinerte formål,2001,11 Samferdselsanlegg,2010,11 Samferdselsanlegg,2020,11 Samferdselsanlegg,2030,11 Samferdselsanlegg,2040,16 Havner og småbåthavner,2044,16 Havner og småbåthavner,2050,11 Samferdselsanlegg,2060,11 Samferdselsanlegg,2070,11 Samferdselsanlegg,2080,11 Samferdselsanlegg,2100,11 Samferdselsanlegg,2800,11 Samferdselsanlegg,3002,12 Blå/grønnstruktur,3020,12 Blå/grønnstruktur,3030,12 Blå/grønnstruktur,3040,12 Blå/grønnstruktur,3050,12 Blå/grønnstruktur,3100,12 Blå/grønnstruktur,3800,12 Blå/grønnstruktur,4001,13 Forsvaret,4010,13 Forsvaret,4020,13 Forsvaret,4030,13 Forsvaret,4800,13 Forsvaret,5100,14 LNFR,5200,15 LNFR spredt,5210,15 LNFR spredt,5220,15 LNFR spredt,5230,15 LNFR spredt,6001,17 Sjø og vassdrag, flerbruk,6100,17 Sjø og vassdrag, flerbruk,6110,17 Sjø og vassdrag, flerbruk,6120,17 Sjø og vassdrag, flerbruk,6130,17 Sjø og vassdrag, flerbruk,6200,17 Sjø og vassdrag, flerbruk,6220,16 Havner og småbåthavner,6230,16 Havner og småbåthavner,6300,17 Sjø og vassdrag, flerbruk,6400,18 Akvakultur,6500,17 Sjø og vassdrag, flerbruk,6600,17 Sjø og vassdrag, flerbruk,6700,17 Sjø og vassdrag, flerbruk,6800,17 Sjø og vassdrag, flerbruk,9999,19 Udefinert
    MAPPING_DIRECTION = FORWARD
    SRC = Arealformålkode
    VAL_ATTR = Arealformålsgruppe
    -> AttributeKeeper_16
AttributeKeeper_16
    CREATE_BULK_MODE_FEATURES = NO
    KEEP_ATTRS = Områdenavn,Plankilde,Arealformålsgruppe,Arealstatus,Planid,KpFormål,RpFormål,Arealformålkode,Ikrafttredelsesdato,Plannavn
    -> AttributeRenamer_9
AttributeRenamer_9
    ATTR_TABLE:
      RENAME_SET_DEFAULT Arealformålkode > Arealformalkode
      RENAME_SET_DEFAULT Arealformålsgruppe > Arealformalsgruppe
      RENAME_SET_DEFAULT KpFormål > KpFormal
      RENAME_SET_DEFAULT Områdenavn > Omradenavn
      RENAME_SET_DEFAULT RpFormål > RpFormal
    MISSING_INPUT_ATTRS = REMOVE
    -> AttributeCreator_16

Bookmark: Reguleringsplan - Klargjøring før kobling med øvrige plandata
Note: Oversette til KpArealformål
AttributeValueMapper_10
    LUT = 100,1001,1000,1001,1001,1001,110,1110,111,1110,1110,1110,1111,1110,1112,1110,1113,1110,1119,2080,112,1110,1120,1120,1121,1120,1122,1120,1123,1120,1124,1120,113,1110,1130,1130,1140,1140,115,1110,1150,1150,1160,1160,1161,1160,1162,1160,1163,1160,1164,1160,1165,1160,1166,1160,1167,1160,1168,1160,1169,1160,1170,1170,1171,1170,1172,1170,1173,1170,1174,1170,120,1150,1200,1200,1201,1200,130,1300,1300,1300,1310,1300,1320,1300,1330,1300,1340,1300,1350,1300,1360,1300,1390,1300,140,1300,1400,1400,1410,1400,1420,1400,1430,1400,1440,1400,1450,1400,1460,1400,1470,1400,1490,1400,150,1120,1500,1500,1501,1500,1502,1500,1510,1500,1520,1500,1530,1500,1540,1500,1541,1500,1542,1500,1550,1500,1560,1500,1570,1500,1587,6230,1588,6230,1589,1500,1590,1500,160,1160,1600,1600,1610,1600,162,1160,1620,1600,163,1160,1630,1600,164,1160,166,1160,167,1160,169,1160,1690,1600,170,1160,1700,1700,1710,1700,172,1160,173,1160,1730,1700,174,1160,176,1160,177,1160,179,1160,180,1170,1800,1800,1801,1800,1802,1800,1803,1800,1804,1800,181,1170,1810,1300,1811,1300,1812,1300,1813,1300,1814,1300,182,1170,1820,1800,1821,1800,1822,1800,1823,1800,1824,1300,1825,1300,1826,1300,1830,1300,1831,1300,190,2080,1900,1800,191,2080,192,1300,199,1500,200,5100,2000,2001,2001,2001,2010,2010,2011,2010,2012,2010,2013,2001,2014,2010,2015,2010,2016,2010,2017,2001,2018,2001,2019,2001,2020,2020,2021,2020,2022,2020,2023,2020,2024,2001,2025,2001,2026,2001,2027,2001,2028,2001,2029,2001,2030,2030,2031,2030,2032,2030,2033,2030,2034,2030,2040,2040,2041,2040,2042,2040,2043,2040,2044,2044,2045,2001,2050,2050,2060,2060,2061,2060,2070,2070,2071,2070,2072,2070,2073,2070,2074,2070,2080,2080,2081,2080,2082,2080,2083,2080,210,5100,2100,2100,2101,2100,2110,2100,2120,2100,2140,2100,2141,2100,2142,2100,2143,2100,2150,2100,2160,2100,2170,2100,2180,2100,2190,2100,220,5100,230,5100,240,1600,2800,2800,2900,2800,299,5100,300,2001,3000,3002,3001,3002,3002,3002,3020,3020,3030,3030,3031,3030,3040,3040,3041,3040,3050,3050,3060,3002,3061,3002,310,2010,3100,3100,311,2010,3110,3100,319,2001,320,2010,321,2010,322,2010,330,2010,331,2001,332,2080,333,2080,340,2060,341,2070,342,2070,343,2070,350,2020,360,2020,370,2030,371,2030,372,2030,380,2040,3800,3800,381,2040,382,6230,390,6200,3900,3800,391,6200,392,6220,398,6200,399,2001,400,3040,4000,4001,4001,4001,4010,4010,4020,4020,4030,4030,410,3050,420,3030,421,3030,430,3040,440,1400,450,3040,459,3040,460,6700,461,6700,462,6230,463,6700,469,6700,4800,4800,4900,4800,500,2100,5000,5100,5001,5100,510,2100,5100,5100,5110,5100,5111,5100,5112,5100,5113,5100,5114,5100,5115,5100,5120,3002,5130,3002,5140,5100,520,1400,5200,5200,5210,5210,5220,5220,5230,5230,530,1500,5300,3002,540,5100,5400,5100,550,5100,5500,3002,5600,3002,590,5100,5900,5100,600,9999,6000,6001,6001,6001,601,2010,6100,6100,611,3002,6110,6110,612,1170,6120,6120,613,3002,6130,6130,614,6700,615,1400,616,1400,617,1700,618,6230,619,6230,620,1500,6200,6200,621,1500,6210,6200,6211,6200,622,6500,6220,6220,623,1500,6230,6230,624,2100,6240,6230,625,2100,626,4001,627,1500,630,6400,6300,6300,631,6400,6310,6300,6320,6300,6330,6600,640,2001,6400,6400,641,2001,6410,6400,6420,6400,6430,6400,645,5100,646,5100,650,3002,6500,6500,651,6600,652,3002,660,9999,6600,6600,661,9999,6610,6600,662,9999,6620,6600,663,3002,670,1200,6700,6700,671,1200,6710,6700,6720,6700,6730,6230,6740,6230,6750,6230,6760,6700,6770,6700,680,5100,6800,6800,681,5100,685,1300,690,1500,6900,6800,691,2001,692,1170,693,1500,699,9999,700,1500,710,2010,720,2010,730,2080,750,1600,760,1110,770,2080,780,3002,790,1500,800,1001,900,1800,910,1800,911,1800,912,1800,913,1800,920,1300,921,1300,922,1300,923,1300,924,1300,930,1300,931,1300,939,1300,960,1160,980,1300,990,1800,991,1500,992,2001,999,9999
    MAPPING_DIRECTION = FORWARD
    SRC = RpFormål
    VAL_ATTR = Arealformålkode
    -> FeatureMerger [REQUESTOR]

Bookmark: Opsjonelt excelark for ekskludering av reguleringsplaner
Note: Opsjonelt excelark med kommunenummer og planidentifikasjon som skal ekskluderes
Ark1 (reader XLSXR_2) [off]
    attributes: Kommune number(5,0), Planid char(12)
    -> Tester_17
Tester_17
    BOOL_OP = OR
    TEST_CLAUSE = TEST @Value(Kommune) = $(Kommune)
    TEST_MODE = TEST
    PASSED -> Junction_3

Bookmark: Kobling for å utelate gitte regplaner
FeatureMerger_3
    ATTR_ACCUM_MODE = Merge Supplier
    ATTR_CONFLICT_RES = Use Requestor
    IGNORE_NULLS = No
    JOIN_KEYS = @Value(Planid) @Value(Planid) AUTO
    MERGE_TYPE = Attributes Only
    PROCESS_DUPS = NO
    REJECT_NULL_MISSING_KEYS = No
    SUPPLIERS_FIRST = No
    UNMERGED_REQUESTOR -> AreaOnAreaOverlayer_2 [AREA]

Bookmark: Planreserveberegning
AttributeCreator_16
    ATTR_TABLE = SET_TO UtbyggingsFormal (varchar(200)) = $(FormalTilBeregning)
    -> Planreserveberegning [PLAN]
Planreserveberegning
    AREALFORMALKODE = @Value(Arealformalkode)
    AREALFORMALSGRUPPE = @Value(Arealformalsgruppe)
    AREALSTATUS = @Value(Arealstatus)
    AREALTYPE = @Value(arealtype)
    HOVEDKLASSE = @Value(hovedklasse)
    IKRAFTTREDELSESDATO = @Value(Ikrafttredelsesdato)
    KPFORMAL = @Value(KpFormal)
    OBJTYPE = @Value(objtype)
    OMRADENAVN = @Value(Omradenavn)
    PLANID = @Value(Planid)
    PLANKILDE = @Value(Plankilde)
    PLANNAVN = @Value(Plannavn)
    RPFORMAL = @Value(RpFormal)
    UNDERKLASSE = @Value(underklasse)
    UTBYGGINGSFORMAL = @Value(UtbyggingsFormal)
    -> AttributeRenamer_10
AttributeRenamer_10
    ATTR_TABLE:
      RENAME_SET_DEFAULT Arealformalkode > Arealformålkode
      RENAME_SET_DEFAULT Arealformalsgruppe > Arealformålsgruppe
      RENAME_SET_DEFAULT KpFormal > KpFormål
      RENAME_SET_DEFAULT Omradenavn > Områdenavn
      RENAME_SET_DEFAULT RpFormal > RpFormål
    MISSING_INPUT_ATTRS = REMOVE
    -> Planreserve
Planreserve: Inspector

FME custom transformer LesGrunndata

Parameters:
- AR5_URL = @Value(AR5_URL)   # Ar5 Url
- BYGNING_URL = @Value(BYGNING_URL)   # Bygning Url
- SSBAREALBRUK_URL = @Value(SSBAREALBRUK_URL)   # Ssbarealbruk Url
- TILTAK_URL = @Value(TILTAK_URL)   # Tiltak Url
- VEG_URL = @Value(VEG_URL)   # Veg Url

Input (input)
    -> FeatureReader_10 [INITIATOR]
    -> FeatureReader_9 [INITIATOR]
    -> FeatureReader_8 [INITIATOR]
    -> FeatureReader_4 [INITIATOR]
    -> FeatureReader_11 [INITIATOR]

Bookmark: FKB Veg og FKB Bygning til planreserveberegning
FeatureReader_10
    ATTRIBUTES = fkb_tiltak_omrade,"OBJECTID,objtype,lokalid,datafangstdato,oppdateringsdato,informasjon,sluttdato,navnerom,versjonid,datafangstmetode,noyaktighet,synbarhet,datafangstmetodehoyde,noyaktighethoyde,eksternpeker,medium,saksreferanse,behandlingsstatus,kartregistrering,behandlingsdato,tiltaksansvarlig,andretiltak,bygningsnummer,bygningsendringlopenummer,hoydereferanse,lavestegulv,hoydeoverbakken,tiltakstypebygning,SHAPE_Length,SHAPE_Area"
    ATTR_ACCUM_MODE = Only Use Result
    COMBINE_GEOM = Use Result
    DATASET = @Value(TILTAK_URL)
    FEATURETYPES = fkb_tiltak_omrade
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    fkb_tiltak_omrade -> CsmapReprojector_13
CsmapReprojector_13
    DEST = ETRS89.UTM-33N
    INTERPOLATION_TYPE_NAME = Nearest Neighbor
    RASTER_CELL_SIZE = Preserve Cells
    RASTER_TOLERANCE = 0.0
    REPROJECTED -> Tester_4
Tester_4
    BOOL_OP = OR
    TEST_CLAUSE = TEST @Value(objtype) = BygningTiltak
    TEST_MODE = TEST
    PASSED -> FKB_Tiltak (output)
FKB_Tiltak (output)
FeatureReader_9
    ATTRIBUTES = fkb_veg_grense,"OBJECTID,objtype,lokalid,navnerom,versjonid,datafangstdato,verifiseringsdato,oppdateringsdato,informasjon,sluttdato,registreringsversjon,datafangstmetode,noyaktighet,synbarhet,datafangstmetodehoyde,noyaktighethoyde,medium,hoydereferanse,vegoverveg,nedsenketkantstein,eksternpeker,nvdbpeker,SHAPE_Length",fkb_veg_omrade,"OBJECTID,objtype,lokalid,navnerom,versjonid,datafangstdato,verifiseringsdato,oppdateringsdato,informasjon,sluttdato,registreringsversjon,medium,eksternpeker,nvdbpeker,funksjon,hoydereferanse,vegbomtype,rekkverkstype,bruksomrade,typeveg,vegkategori,vegfase,vegnummer,vegoverveg,nedsenketkantstein,SHAPE_Length,SHAPE_Area",fkb_veg_senterlinje,"OBJECTID,objtype,lokalid,navnerom,versjonid,datafangstdato,verifiseringsdato,oppdateringsdato,informasjon,sluttdato,registreringsversjon,datafangstmetode,noyaktighet,synbarhet,datafangstmetodehoyde,noyaktighethoyde,funksjon,hoydereferanse,vegbomtype,rekkverkstype,bruksomrade,eksternpeker,nvdbpeker,SHAPE_Length"
    ATTR_ACCUM_MODE = Only Use Result
    COMBINE_GEOM = Use Result
    DATASET = @Value(VEG_URL)
    FEATURETYPES = fkb_veg_omrade
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    fkb_veg_omrade -> CsmapReprojector_9
CsmapReprojector_9
    DEST = ETRS89.UTM-33N
    INTERPOLATION_TYPE_NAME = Nearest Neighbor
    RASTER_CELL_SIZE = Preserve Cells
    RASTER_TOLERANCE = 0.0
    REPROJECTED -> FKB_Veg (output)
FKB_Veg (output)
FeatureReader_8
    ATTRIBUTES = fkb_bygning_grense,"OBJECTID,objtype,lokalid,datafangstdato,verifiseringsdato,oppdateringsdato,informasjon,sluttdato,registreringsversjon,navnerom,versjonid,datafangstmetode,noyaktighet,synbarhet,datafangstmetodehoyde,noyaktighethoyde,hoydereferanse,medium,tredniva,skalavgrensebygning,takskjegg,lavestegulv,SHAPE_Length",fkb_bygning_omrade,"OBJECTID,objtype,lokalid,datafangstdato,verifiseringsdato,oppdateringsdato,informasjon,sluttdato,registreringsversjon,navnerom,versjonid,datafangstmetode,noyaktighet,synbarhet,datafangstmetodehoyde,noyaktighethoyde,hoydereferanse,medium,bygningsnummer,bygningstype,bygningsstatus,kommunenummer,SHAPE_Length,SHAPE_Area",fkb_bygning_posisjon,"OBJECTID,objtype,lokalid,datafangstdato,verifiseringsdato,oppdateringsdato,informasjon,sluttdato,registreringsversjon,navnerom,versjonid,datafangstmetode,noyaktighet,synbarhet,datafangstmetodehoyde,noyaktighethoyde,hoydereferanse,medium,bygningsnummer,bygningstype,bygningsstatus,kommunenummer,tredniva",fkb_bygning_senterlinje,"OBJECTID,objtype,lokalid,datafangstdato,verifiseringsdato,oppdateringsdato,informasjon,sluttdato,registreringsversjon,navnerom,versjonid,datafangstmetode,noyaktighet,synbarhet,datafangstmetodehoyde,noyaktighethoyde,hoydereferanse,medium,tredniva,SHAPE_Length"
    ATTR_ACCUM_MODE = Only Use Result
    COMBINE_GEOM = Use Result
    DATASET = @Value(BYGNING_URL)
    FEATURETYPES = fkb_bygning_omrade
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    fkb_bygning_omrade -> CsmapReprojector_7
CsmapReprojector_7
    DEST = ETRS89.UTM-33N
    INTERPOLATION_TYPE_NAME = Nearest Neighbor
    RASTER_CELL_SIZE = Preserve Cells
    RASTER_TOLERANCE = 0.0
    REPROJECTED -> Tester_3
Tester_3
    BOOL_OP = OR
    TEST_CLAUSE = TEST @Value(objtype) IN AnnenBygning,Bygning
    TEST_MODE = TEST
    PASSED -> FKB_Bygning (output)
FKB_Bygning (output)

Bookmark: AR5 og SSB Arealbruk
FeatureReader_4
    ATTRIBUTES = fkb_ar5_grense,"OBJECTID,objtype,lokalid,datafangstdato,verifiseringsdato,oppdateringsdato,informasjon,sluttdato,registreringsversjon,avgrensingtype,navnerom,versjonid,datafangstmetode,noyaktighet,synbarhet,opphav,SHAPE_Length",fkb_ar5_omrade,"OBJECTID,objtype,lokalid,datafangstdato,verifiseringsdato,oppdateringsdato,informasjon,sluttdato,registreringsversjon,navnerom,versjonid,opphav,arealtype,treslag,skogbonitet,grunnforhold,klassifiseringsmetode,SHAPE_Length,SHAPE_Area"
    ATTR_ACCUM_MODE = Only Use Result
    COMBINE_GEOM = Use Result
    DATASET = @Value(AR5_URL)
    FEATURETYPES = fkb_ar5_omrade
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    fkb_ar5_omrade -> CsmapReprojector_6
CsmapReprojector_6
    DEST = ETRS89.UTM-33N
    INTERPOLATION_TYPE_NAME = Nearest Neighbor
    RASTER_CELL_SIZE = Preserve Cells
    RASTER_TOLERANCE = 0.0
    REPROJECTED -> AttributeKeeper_13
AttributeKeeper_13
    CREATE_BULK_MODE_FEATURES = NO
    KEEP_ATTRS = arealtype,grunnforhold,skogbonitet,treslag
    -> FKB_AR5 (output)
FKB_AR5 (output)
FeatureReader_11
    ATTRIBUTES = ssbarealbrukflate,"OBJECTID,objtype,lokalid,navnerom,versjonid,datauttaksdato,malemetode,opphav,kilde,hovedklasse,underklasse,SHAPE_Length,SHAPE_Area",ssbarealbrukflate_informasjon,"OBJECTID,ssbarealbrukflate_fk,informasjon",ssbarealbrukflate_kommune,"OBJECTID,ssbarealbrukflate_fk,kommunenummer_fk",ssbarealbrukflate_prosesshistorie,"OBJECTID,ssbarealbrukflate_fk,prosesshistorie"
    ATTR_ACCUM_MODE = Only Use Result
    COMBINE_GEOM = Use Result
    DATASET = @Value(SSBAREALBRUK_URL)
    FEATURETYPES = ssbarealbrukflate
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    ssbarealbrukflate -> CsmapReprojector_5
CsmapReprojector_5
    DEST = ETRS89.UTM-33N
    INTERPOLATION_TYPE_NAME = Nearest Neighbor
    RASTER_CELL_SIZE = Preserve Cells
    RASTER_TOLERANCE = 0.0
    REPROJECTED -> AttributeKeeper_6
AttributeKeeper_6
    CREATE_BULK_MODE_FEATURES = NO
    KEEP_ATTRS = hovedklasse,underklasse
    -> SSB_Arealbruk (output)
SSB_Arealbruk (output)

FME custom transformer LesPlandata

Parameters:
- Kommune = 4212
- OUTPUT =   # Output
- DEST = ETRS89.UTM-33N   # EnableReadFromFeature:Yes Velg output-koordinatsystem
- KDP_URL = @Value(KDP_URL)   # Kdp Url
- KP_URL = @Value(KP_URL)   # Kp Url
- RP_URL = @Value(RP_URL)   # Rp Url

Input (input)
    -> FeatureReader_12 [INITIATOR]
    -> Tester_2
    -> FeatureReader_3 [INITIATOR]
FeatureReader_12
    ATTRIBUTES = AREALST_SOSI,"AREALST,SOSI_parent_guid",AnnenBygning,"OBJTYPE,DATO,PTEMA,AREALST,OPLAREAL,MALEMETODE,NOYAKTIGHET,SYNBARHET",FTEMA_SOSI,"FTEMA,SOSI_parent_guid",GrunnkretsGrense,"OBJTYPE,LTEMA,DATO",IpGrense,"OBJTYPE,LTEMA,DATO",KpArealGrense,"OBJTYPE,DATO,LTEMA,AREALST,OPLAREAL,MALEMETODE,NOYAKTIGHET,SYNBARHET,SOSI_guid",KpArealbrukOmrade,"OBJTYPE,FTEMA,DATO,OPLAREAL,AREALST,OMRNAVN,MALEMETODE,NOYAKTIGHET,SYNBARHET",KpArealformalOmrade,"OBJTYPE,AREALST,DATO,FTEMA,OPLAREAL,OMRNAVN,OPLRETNL,MALEMETODE,NOYAKTIGHET,SYNBARHET,SOSI_guid",KpArealformalOmrade_1,"OBJTYPE,AREALST,DATO,OPLAREAL,PTEMA",KpDetaljeringGrense,"OBJTYPE,AREALST,DATO,LTEMA,VERTNIV",KpGrense,"OBJTYPE,LTEMA,DATO,SOSI_guid",KpInfrastrukturLinje,"OBJTYPE,AREALST,DATO,LTEMA",KpOmrade,"OBJTYPE,FTEMA,DATO",KpPaskrift,"OBJTYPE,TTEMA,DATO,STRENG,OBJEKT_X,OBJEKT_Y",KpRestriksjonGrense,"OBJTYPE,LTEMA,DATO,SOSI_guid",KpRestriksjonOmrade,"OBJTYPE,FTEMA,DATO,OPLRESTR,AREALST,OMRNAVN",KpRetningslinjeGrense,"OBJTYPE,LTEMA,DATO,MALEMETODE,NOYAKTIGHET,SYNBARHET,SOSI_guid",KpRetningslinjeOmrade,"OBJTYPE,FTEMA,DATO,OPLRETNL,OMRNAVN,MALEMETODE,NOYAKTIGHET,SYNBARHET,SOSI_guid",KpSamferdselLinje,"OBJTYPE,AREALST,DATO,LTEMA,VERTNIV,SYNBARHET,SOSI_guid",Kulturminne,"OBJTYPE,PTEMA,DATO",LTEMA_SOSI,"LTEMA,SOSI_parent_guid",OMRNAVN_SOSI,"OMRNAVN,SOSI_parent_guid",OPLAREAL_SOSI,"OPLAREAL,SOSI_parent_guid",OPLRETNL_SOSI,"OPLRETNL,SOSI_parent_guid",SOSI_RelationshipClasses,,Snoscooterloype,"OBJTYPE,AREALST,DATO,LTEMA,SOSI_guid",Unknown,"DATO,LTEMA,AREALST,MALEMETODE,NOYAKTIGHET,SYNBARHET",Unknown_1,"DATO,STRENG,TTEMA,OBJEKT_X,OBJEKT_Y",Unknown_2,"AREALST,DATO,LTEMA,OMRNAVN,OPLAREAL,OPLRETNL,MALEMETODE,NOYAKTIGHET,SYNBARHET"
    ATTR_ACCUM_MODE = Only Use Result
    COMBINE_GEOM = Use Result
    DATASET = @Value(KP_URL)
    FEATURETYPES = KpArealbrukOmrade KpArealformalOmrade KpOmrade
    FORMAT = SOSI
    INTERACT = NONE
    ORDER_RESULTS = No
    OUTPUT_FEATURES_DISPLAY = Schema and Data Features
    SOSI_READER_ALLOW_MISSING_MANDATORY_ATTRS = yes
    SOSI_READER_ATTRIBUTE_VALIDATION_LEVEL = Basic
    SOSI_READER_DEFAULT_FONT_SIZE = 8.0
    SOSI_READER_ENFORCE_Z_VALUES = Auto-detect
    SOSI_READER_LOG_ERRORS = yes
    SOSI_READER_LOG_WARNINGS = no
    SOSI_READER_MISSING_Z_VALUE = -9999
    SOSI_READER_REFERENCE_SCALE = 1000
    KpArealbrukOmrade -> CsmapReprojector_3
    KpArealformalOmrade -> CsmapReprojector_3
CsmapReprojector_3
    DEST = $(DEST)
    INTERPOLATION_TYPE_NAME = Nearest Neighbor
    RASTER_CELL_SIZE = Preserve Cells
    RASTER_TOLERANCE = 0.0
    REPROJECTED -> Clipper_3 [CANDIDATE]
Tester_2
    BOOL_OP = OR
    TEST_CLAUSE = TEST KDP_URL ATTRIBUTE_HAS_A_VALUE ""
    TEST_MODE = TEST
    PASSED -> FeatureReader_2 [INITIATOR]
FeatureReader_2
    ATTRIBUTES = KpAngittHensynGrense,"OBJTYPE,FORSTEDIGITALISERINGSDATO,MALEMETODE,NOYAKTIGHET",KpAngittHensynSone,"OBJTYPE,KPANGITTHENSYN,HENSYNSONENAVN,FORSTEDIGITALISERINGSDATO,PLANID,KOMM",KpArealGrense,"OBJTYPE,FORSTEDIGITALISERINGSDATO,MALEMETODE,NOYAKTIGHET,LOKALID,NAVNEROM",KpArealGrense_1,"OBJTYPE,FORSTEDIGITALISERINGSDATO,MALEMETODE,LOKALID,NAVNEROM,NOYAKTIGHET",KpArealbrukOmrade,"OBJTYPE,OPLAREAL,AREALST,OPLAREALUTDYP,OMRNAVN,FORSTEDIGITALISERINGSDATO,KOMM,PLANID,LOKALID,NAVNEROM",KpArealformalOmrade,"OBJTYPE,KPAREALFORMAL,AREALST,EIERFORM,FORSTEDIGITALISERINGSDATO,OMRNAVN,BESKRIVELSE,PLANID,KOMM,LOKALID,NAVNEROM",KpBandleggingGrense,"OBJTYPE,AREALST,FORSTEDIGITALISERINGSDATO,MALEMETODE,NOYAKTIGHET",KpBandleggingSone,"OBJTYPE,KPBANDLEGGING,AREALST,HENSYNSONENAVN,FORSTEDIGITALISERINGSDATO,PLANID,KOMM",KpDetaljeringGrense,"OBJTYPE,FORSTEDIGITALISERINGSDATO,MALEMETODE,NOYAKTIGHET",KpDetaljeringGrense_1,"OBJTYPE,FORSTEDIGITALISERINGSDATO,MALEMETODE,NOYAKTIGHET",KpDetaljeringSone,"OBJTYPE,KPDETALJERING,HENSYNSONENAVN,FORSTEDIGITALISERINGSDATO,PLANID,KOMM",KpFareGrense,"OBJTYPE,FORSTEDIGITALISERINGSDATO,MALEMETODE,NOYAKTIGHET,LOKALID,NAVNEROM",KpFareSone,"OBJTYPE,KPFARE,HENSYNSONENAVN,FORSTEDIGITALISERINGSDATO,PLANID,KOMM,LOKALID,NAVNEROM",KpGrense,"OBJTYPE,FORSTEDIGITALISERINGSDATO,LOKALID,NAVNEROM,MALEMETODE,NOYAKTIGHET",KpGrense_1,"OBJTYPE,FORSTEDIGITALISERINGSDATO,MALEMETODE,NOYAKTIGHET",KpInfrastrukturGrense,"OBJTYPE,FORSTEDIGITALISERINGSDATO",KpInfrastrukturSone,"OBJTYPE,KPINFRASTRUKTUR,HENSYNSONENAVN,FORSTEDIGITALISERINGSDATO,PLANID,KOMM",KpOmrade,"OBJTYPE,PLANTYPE,PLANSTAT,PLANBEST,LOVREFERANSE,PLANNAVN,FORSTEDIGITALISERINGSDATO,OPPRINNELIGPLANID,OPPRINNELIGADMINISTRATIVENHET,KOMM,PLANID,LOKALID,NAVNEROM",KpPaskrift,"OBJTYPE,STRENG,FORSTEDIGITALISERINGSDATO,PLANPASKRIFTTYPE,KOMM,PLANID,LOKALID,NAVNEROM,OBJEKT_X,OBJEKT_Y",KpRestriksjonGrense,"OBJTYPE,FORSTEDIGITALISERINGSDATO,MALEMETODE,NOYAKTIGHET,LOKALID,NAVNEROM",KpRestriksjonOmrade,"OBJTYPE,OPLRESTR,FORSTEDIGITALISERINGSDATO,KOMM,PLANID",KpSamferdselLinje,"OBJTYPE,TYPESAMFLINJE,VERTNIV,AREALST,FORSTEDIGITALISERINGSDATO,KOMM,PLANID,MALEMETODE,NOYAKTIGHET",KpSamferdselLinje_1,"OBJTYPE,TYPESAMFLINJE,VERTNIV,AREALST,FORSTEDIGITALISERINGSDATO,PLANID,KOMM,MALEMETODE,NOYAKTIGHET",KpSamferdselPunkt,"OBJTYPE,TYPESAMFPUNKT,VERTNIV,AREALST,VIKTIG,PLANID,KOMM,ROTASJON,OBJEKT_X,OBJEKT_Y",KpSikringGrense,OBJTYPE,KpSikringSone,"OBJTYPE,KPSIKRING,HENSYNSONENAVN,BESKRIVELSE,KOMM,PLANID",KpStoyGrense,"OBJTYPE,FORSTEDIGITALISERINGSDATO,LOKALID,NAVNEROM",KpStoyGrense_1,"OBJTYPE,FORSTEDIGITALISERINGSDATO",KpStoySone,"OBJTYPE,KPSTOY,HENSYNSONENAVN,FORSTEDIGITALISERINGSDATO,PLANID,KOMM,LOKALID,NAVNEROM"
    ATTR_ACCUM_MODE = Only Use Result
    COMBINE_GEOM = Use Result
    DATASET = @Value(KDP_URL)
    FEATURETYPES = KpArealformalOmrade KpArealbrukOmrade KpOmrade
    FORMAT = SOSI
    INTERACT = NONE
    ORDER_RESULTS = No
    OUTPUT_FEATURES_DISPLAY = Schema and Data Features
    SOSI_READER_ALLOW_MISSING_MANDATORY_ATTRS = yes
    SOSI_READER_ATTRIBUTE_VALIDATION_LEVEL = Basic
    SOSI_READER_DEFAULT_FONT_SIZE = 8.0
    SOSI_READER_ENFORCE_Z_VALUES = Auto-detect
    SOSI_READER_LOG_ERRORS = yes
    SOSI_READER_LOG_WARNINGS = no
    SOSI_READER_MISSING_Z_VALUE = -9999
    SOSI_READER_REFERENCE_SCALE = 1000
    KpArealformalOmrade -> CsmapReprojector_4
    KpArealbrukOmrade -> CsmapReprojector_4
CsmapReprojector_4
    DEST = $(DEST)
    INTERPOLATION_TYPE_NAME = Nearest Neighbor
    RASTER_CELL_SIZE = Preserve Cells
    RASTER_TOLERANCE = 0.0
    REPROJECTED -> Clipper_3 [CLIPPER]
    REPROJECTED -> AttributeRenamer_11
Clipper_3
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeRenamer_11
AttributeRenamer_11
    ATTR_TABLE:
      RENAME_SET_DEFAULT KPAREALFORMAL > KpFormål
      RENAME_SET_DEFAULT OPLAREAL > KpFormål
      RENAME_SET_DEFAULT AREALST > Arealstatus
      RENAME_SET_DEFAULT OBJTYPE > Plankilde
      RENAME_SET_DEFAULT OMRNAVN > Områdenavn
      RENAME_SET_DEFAULT arealbruksstatus > Arealstatus
      RENAME_SET_DEFAULT objtype > Plankilde
      RENAME_SET_DEFAULT omradenavn > Områdenavn
      RENAME_SET_DEFAULT arealformal > KpFormål
    MISSING_INPUT_ATTRS = PRESERVE
    -> Kommuneplan (output)
Kommuneplan (output)
FeatureReader_3
    ATTRIBUTES = PblMidlByggAnleggGrense,"OBJECTID,objtype,forstedigitaliseringsdato,oppdateringsdato,malemetode,noyaktighet,omradeid,originaldatavert,kopidato,lokalid,navnerom,versjonid,SHAPE_Length",PblMidlByggAnleggOmrade,"OBJECTID,objtype,kommunenummer,planidentifikasjon,bestemmelseomradenavn,saksar,sakssekvensnummer,avgjorelsesdato,gyldigtildato,vertikalniva,forstedigitaliseringsdato,oppdateringsdato,omradeid,originaldatavert,kopidato,lokalid,navnerom,versjonid,SHAPE_Length,SHAPE_Area",RbBevaringGrense,"OBJECTID,objtype,forstedigitaliseringsdato,oppdateringsdato,malemetode,noyaktighet,omradeid,originaldatavert,kopidato,lokalid,navnerom,versjonid,SHAPE_Length",RbBevaringOmrade,"OBJECTID,objtype,kommunenummer,planidentifikasjon,reguleringsformal,vertikalniva,feltbetegnelse,forstedigitaliseringsdato,oppdateringsdato,omradeid,originaldatavert,kopidato,lokalid,navnerom,versjonid,SHAPE_Length,SHAPE_Area",RbFareOmrade,"OBJECTID,objtype,kommunenummer,planidentifikasjon,reguleringsformal,vertikalniva,feltbetegnelse,reguleringsformalsutdyping,forstedigitaliseringsdato,oppdateringsdato,omradeid,originaldatavert,kopidato,lokalid,navnerom,versjonid,SHAPE_Length,SHAPE_Area",RbFormalOmrade,"OBJECTID,objtype,kommunenummer,planidentifikasjon,reguleringsformal,reguleringsformalsutdyping,vertikalniva,feltbetegnelse,utnyttingstype,utnyttingstall,utnyttingstall_minimum,uteoppholdsareal,byggverkbestemmelse,avkjorselsbestemmelse,forstedigitaliseringsdato,oppdateringsdato,omradeid,originaldatavert,kopidato,lokalid,navnerom,versjonid,SHAPE_Length,SHAPE_Area",RbRestriksjonGrense,"OBJECTID,objtype,forstedigitaliseringsdato,oppdateringsdato,malemetode,noyaktighet,omradeid,originaldatavert,kopidato,lokalid,navnerom,versjonid,SHAPE_Length",RbRestriksjonOmrade,"OBJECTID,objtype,kommunenummer,planidentifikasjon,reguleringsformal,vertikalniva,feltbetegnelse,forstedigitaliseringsdato,oppdateringsdato,omradeid,originaldatavert,kopidato,lokalid,navnerom,versjonid,SHAPE_Length,SHAPE_Area",RpAngittHensynGrense,"OBJECTID,objtype,forstedigitaliseringsdato,oppdateringsdato,malemetode,noyaktighet,omradeid,originaldatavert,kopidato,lokalid,navnerom,versjonid,SHAPE_Length",RpAngittHensynSone,"OBJECTID,objtype,kommunenummer,planidentifikasjon,angitthensyn,hensynsonenavn,beskrivelse,vertikalniva,forstedigitaliseringsdato,oppdateringsdato,omradeid,originaldatavert,kopidato,lokalid,navnerom,versjonid,SHAPE_Length,SHAPE_Area",RpArealformalOmrade,"OBJECTID,objtype,kommunenummer,planidentifikasjon,arealformal,vertikalniva,eierform,utnyttingstype,utnyttingstall,utnyttingstall_minimum,beskrivelse,feltbetegnelse,uteoppholdsareal,byggverkbestemmelse,avkjorselsbestemmelse,forstedigitaliseringsdato,oppdateringsdato,omradeid,originaldatavert,kopidato,lokalid,navnerom,versjonid,SHAPE_Length,SHAPE_Area",RpArealformal_rputnytt,"OBJECTID,rparealformalomrade_fk,utnyttingstype,utnyttingstall,utnyttingstall_minimum",RpBandleggingGrense,"OBJECTID,objtype,forstedigitaliseringsdato,oppdateringsdato,malemetode,noyaktighet,omradeid,originaldatavert,kopidato,lokalid,navnerom,versjonid,SHAPE_Length",RpBandleggingSone,"OBJECTID,objtype,kommunenummer,planidentifikasjon,bandlegging,bandlagtfremtil,hensynsonenavn,beskrivelse,vertikalniva,forstedigitaliseringsdato,oppdateringsdato,omradeid,originaldatavert,kopidato,lokalid,navnerom,versjonid,SHAPE_Length,SHAPE_Area",RpBestemmelseGrense,"OBJECTID,objtype,forstedigitaliseringsdato,oppdateringsdato,malemetode,noyaktighet,omradeid,originaldatavert,kopidato,lokalid,navnerom,versjonid,SHAPE_Length",RpBestemmelseOmrade,"OBJECTID,objtype,kommunenummer,planidentifikasjon,bestemmelseomradenavn,type,vertikalniva,forstedigitaliseringsdato,oppdateringsdato,omradeid,originaldatavert,kopidato,lokalid,navnerom,versjonid,SHAPE_Length,SHAPE_Area",RpFareGrense,"OBJECTID,objtype,forstedigitaliseringsdato,oppdateringsdato,malemetode,noyaktighet,omradeid,originaldatavert,kopidato,lokalid,navnerom,versjonid,SHAPE_Length",RpFareSone,"OBJECTID,objtype,kommunenummer,planidentifikasjon,fare,hensynsonenavn,beskrivelse,vertikalniva,forstedigitaliseringsdato,oppdateringsdato,omradeid,originaldatavert,kopidato,lokalid,navnerom,versjonid,SHAPE_Length,SHAPE_Area",RpFormalGrense,"OBJECTID,objtype,forstedigitaliseringsdato,oppdateringsdato,malemetode,noyaktighet,omradeid,originaldatavert,kopidato,lokalid,navnerom,versjonid,SHAPE_Length",RpGrense,"OBJECTID,objtype,forstedigitaliseringsdato,oppdateringsdato,malemetode,noyaktighet,omradeid,originaldatavert,kopidato,lokalid,navnerom,versjonid,SHAPE_Length",RpJuridiskLinje,"OBJECTID,objtype,kommunenummer,planidentifikasjon,juridisklinje,vertikalniva,forstedigitaliseringsdato,oppdateringsdato,malemetode,noyaktighet,omradeid,originaldatavert,kopidato,lokalid,navnerom,versjonid,SHAPE_Length",RpJuridiskSymbol,"OBJECTID,FeatureID,ZOrder,AnnotationClassID,Element,SymbolID,Status,TextString,FontName,FontSize,Bold,Italic,Underline,VerticalAlignment,HorizontalAlignment,XOffset,YOffset,Angle,FontLeading,WordSpacing,CharacterWidth,CharacterSpacing,FlipAngle,Override,SHAPE_Length,SHAPE_Area,objtype,kommunenummer,planidentifikasjon,juridiskpunkt,vertikalniva,forstedigitaliseringsdato,oppdateringsdato,malemetode,noyaktighet,omradeid,originaldatavert,kopidato,lokalid,navnerom,versjonid",RpOmrade,"OBJECTID,objtype,kommunenummer,planidentifikasjon,plannavn,plantype,planstatus,planbestemmelse,vertikalniva,lovreferanse,ikrafttredelsesdato,lovreferansebeskrivelse,forslagsstillertype,vedtakendeligplandato,kunngjoringsdato,opprinneligadministrativenhet,opprinneligplanid,forstedigitaliseringsdato,oppdateringsdato,informasjon,link,prosesshistorie,omradeid,originaldatavert,kopidato,lokalid,navnerom,versjonid,SHAPE_Length,SHAPE_Area",RpOmrade_link,"OBJECTID,rpomrade_fk,link",RpPaskrift,"OBJECTID,FeatureID,ZOrder,AnnotationClassID,Element,SymbolID,Status,TextString,FontName,FontSize,Bold,Italic,Underline,VerticalAlignment,HorizontalAlignment,XOffset,YOffset,Angle,FontLeading,WordSpacing,CharacterWidth,CharacterSpacing,FlipAngle,Override,SHAPE_Length,SHAPE_Area,objtype,kommunenummer,planidentifikasjon,vertikalniva,generelltekststreng,paskrifttype,forstedigitaliseringsdato,oppdateringsdato,malemetode,noyaktighet,omradeid,originaldatavert,kopidato,lokalid,navnerom,versjonid",RpRegulertHoyde,"OBJECTID,objtype,kommunenummer,planidentifikasjon,regulerthoyde,hoydereferansesystem,vertikalniva,forstedigitaliseringsdato,oppdateringsdato,malemetode,noyaktighet,omradeid,originaldatavert,kopidato,lokalid,navnerom,versjonid,SHAPE_Length",RpSikringGrense,"OBJECTID,objtype,forstedigitaliseringsdato,oppdateringsdato,malemetode,noyaktighet,omradeid,originaldatavert,kopidato,lokalid,navnerom,versjonid,SHAPE_Length",RpSikringSone,"OBJECTID,objtype,kommunenummer,planidentifikasjon,sikring,hensynsonenavn,beskrivelse,vertikalniva,forstedigitaliseringsdato,oppdateringsdato,omradeid,originaldatavert,kopidato,lokalid,navnerom,versjonid,SHAPE_Length,SHAPE_Area",RpStoyGrense,"OBJECTID,objtype,forstedigitaliseringsdato,oppdateringsdato,malemetode,noyaktighet,omradeid,originaldatavert,kopidato,lokalid,navnerom,versjonid,SHAPE_Length",RpStoySone,"OBJECTID,objtype,kommunenummer,planidentifikasjon,stoy,hensynsonenavn,beskrivelse,vertikalniva,forstedigitaliseringsdato,oppdateringsdato,omradeid,originaldatavert,kopidato,lokalid,navnerom,versjonid,SHAPE_Length,SHAPE_Area"
    ATTR_ACCUM_MODE = Only Use Result
    COMBINE_GEOM = Use Result
    DATASET = @Value(RP_URL)
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Schema and Data Features
    SELECTED_PORTS = RbFormalOmrade RpArealformalOmrade RpOmrade
    RbFormalOmrade -> CsmapReprojector
    RpArealformalOmrade -> CsmapReprojector
    RpOmrade -> CsmapReprojector_14
CsmapReprojector
    DEST = $(DEST)
    INTERPOLATION_TYPE_NAME = Nearest Neighbor
    RASTER_CELL_SIZE = Preserve Cells
    RASTER_TOLERANCE = 0.0
    REPROJECTED -> AttributeKeeper_5
AttributeKeeper_5
    CREATE_BULK_MODE_FEATURES = NO
    KEEP_ATTRS = arealformal,objtype,planidentifikasjon,reguleringsformal,kommunenummer,OBJTYPE,PLANID,RPAREALFORMAL,KOMM,REGFORM
    -> AttributeRenamer_4
AttributeRenamer_4
    ATTR_TABLE:
      RENAME_SET_DEFAULT arealformal > RpFormål
      RENAME_SET_DEFAULT objtype > Plankilde
      RENAME_SET_DEFAULT planidentifikasjon > Planid
      RENAME_SET_DEFAULT RPAREALFORMAL > RpFormål
      RENAME_SET_DEFAULT OBJTYPE > Plankilde
      RENAME_SET_DEFAULT PLANID > Planid
      RENAME_SET_DEFAULT REGFORM > RpFormål
      RENAME_SET_DEFAULT reguleringsformal > RpFormål
      RENAME_SET_DEFAULT KOMM > kommunenummer
    MISSING_INPUT_ATTRS = PRESERVE
    -> Reguleringsplan (output)
Reguleringsplan (output)
CsmapReprojector_14
    DEST = $(DEST)
    INTERPOLATION_TYPE_NAME = Nearest Neighbor
    RASTER_CELL_SIZE = Preserve Cells
    RASTER_TOLERANCE = 0.0
    REPROJECTED -> AttributeKeeper_17
AttributeKeeper_17
    CREATE_BULK_MODE_FEATURES = NO
    KEEP_ATTRS = ikrafttredelsesdato,planidentifikasjon,kommunenummer,plannavn,planstatus,IKRAFT,KOMM,PLANID,PLANNAVN,PLANSTATUS
    -> AttributeRenamer_12
AttributeRenamer_12
    ATTR_TABLE:
      RENAME_SET_DEFAULT plannavn > Plannavn
      RENAME_SET_DEFAULT ikrafttredelsesdato > Ikrafttredelsesdato
      RENAME_SET_DEFAULT PLANNAVN > Plannavn
      RENAME_SET_DEFAULT IKRAFT > Ikrafttredelsesdato
      RENAME_SET_DEFAULT KOMM > kommunenummer
      RENAME_SET_DEFAULT PLANID > planidentifikasjon
    MISSING_INPUT_ATTRS = PRESERVE
    -> Tester
Note: Planstatus = 3
Tester
    BOOL_OP = OR
    TEST_CLAUSE = TEST @Value(planstatus) = 3
    TEST_MODE = TEST
    PASSED -> RpOmråde (output)
RpOmråde (output)

Bookmark: Kommuneplaner/-delplaner og reguleringsplaner
Note: NB! / Dersom kommuneplanen ikke kommer med, kan du sjekke om inputen har andre navn på objekttyper/feature types enn det som er i henhold til standard. Inspiser i så fall input og legg til aktuell objekttype i "features types to read" i featureReader . / En gjenganger er at noen kommuneplaner har objekttypen KpArealformalOmrade_1

FME custom transformer Planreserveberegning

Parameters:
- HOVEDKLASSE = @Value(hovedklasse)   # hovedklasse
- UNDERKLASSE = @Value(underklasse)   # underklasse
- AREALSTATUS = @Value(Arealstatus)   # Arealstatus
- PLANID = @Value(Planid)   # Planid
- PLANKILDE = @Value(Plankilde)   # Plankilde
- AREALFORMALKODE = @Value(Arealformalkode)   # Arealformalkode
- AREALFORMALSGRUPPE = @Value(Arealformalsgruppe)   # Arealformalsgruppe
- KPFORMAL = @Value(KpFormal)   # KpFormal
- OMRADENAVN = @Value(Omradenavn)   # Omradenavn
- RPFORMAL = @Value(RpFormal)   # RpFormal
- IKRAFTTREDELSESDATO = @Value(Ikrafttredelsesdato)   # Ikrafttredelsesdato
- PLANNAVN = @Value(Plannavn)   # Plannavn
- OBJTYPE = @Value(objtype)   # objtype
- UTBYGGINGSFORMAL = @Value(UtbyggingsFormal)   # UtbyggingsFormal
- AREALTYPE = @Value(arealtype)   # arealtype

Note: Arealformål som beregnes: / 1001 1110 1120 1130 1140 1150 1160 / 1200 1300 1400 1800 / 2010 / 2080
AR5 (input)
    -> AreaCalculator_2
AreaCalculator_2
    AREA_ATTR = _area
    AREA_TYPE = Plane Area
    MULT = 1
    -> Tester_4
Tester_4
    BOOL_OP = COMPOSITE
    COMPOSITE_TEST = 1 AND 2
    TEST_CLAUSE:
      TEST @Value(arealtype) = 81
      TEST @Value(_area) > 500
    TEST_MODE = TEST
    PASSED -> Dissolver_3
SSB (input)
    -> Tester_3
Tester_3
    BOOL_OP = OR
    TEST_CLAUSE:
      TEST hovedklasse ATTRIBUTE_VALUE_NULL ""
      TEST hovedklasse ATTRIBUTE_IS_MISSING ""
    TEST_MODE = TEST
    FAILED -> Dissolver_3
Dissolver_3
    ACCUM_INPUT_ATTRS = Use Attributes From One Feature
    CLEANING_TOLERANCE = Automatic
    CONNECT_Z_MODE = First Wins
    DEAGGREGATE_INPUT = Yes
    AREA -> Clipper_3 [CLIPPER]
PLAN (input)
    -> AttributeKeeper_3
AttributeKeeper_3
    CREATE_BULK_MODE_FEATURES = NO
    KEEP_ATTRS = Arealstatus,Planid,Plankilde,Arealformalkode,Arealformalsgruppe,KpFormal,Omradenavn,RpFormal,Ikrafttredelsesdato,Plannavn,UtbyggingsFormal
    -> Tester_11
    -> Junction
Tester_11
    BOOL_OP = OR
    TEST_CLAUSE = TEST @Value(Arealformalkode) IN @Value(UtbyggingsFormal)
    TEST_MODE = TEST
    PASSED -> Clipper_3 [CANDIDATE]
Clipper_3
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator_7
Deaggregator_7
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Dissolver
Dissolver
    ACCUM_INPUT_ATTRS = Use Attributes From One Feature
    CLEANING_TOLERANCE = Automatic
    CONNECT_Z_MODE = First Wins
    DEAGGREGATE_INPUT = Yes
    GROUP_BY = Arealformalkode Plankilde
    AREA -> AreaCalculator_6
AreaCalculator_6
    AREA_ATTR = _area
    AREA_TYPE = Plane Area
    MULT = 1
    -> Tester_8
Note: Filtrerer bort små flater (< 250 kvm)
Tester_8
    BOOL_OP = OR
    TEST_CLAUSE = TEST @Value(_area) > 250
    TEST_MODE = TEST
    PASSED -> Tester_7
Tester_7
    BOOL_OP = OR
    TEST_CLAUSE:
      TEST @Value(Arealformalkode) = 2010
      TEST @Value(Arealformalkode) = 2080
    TEST_MODE = TEST
    PASSED -> Clipper_4 [CANDIDATE]
    FAILED -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator
Deaggregator
    EXPLODE_INSTANCES = No
    GEOM_NAME_FIELD = _geometry_name
    LIST_ATTR_MODE_LOOKUP = LEAN
    MODE = Flatten All Levels
    SPLIT_COMPOSITES = No
    DEAGGREGATED -> Tester
Note: 30 m buffer fra bygg på Kp-formål med unntak av bolig (1110). 10 m for øvrige planer
Tester
    BOOL_OP = COMPOSITE
    COMPOSITE_TEST = 1 AND 2 AND 3
    TEST_CLAUSE:
      TEST @Value(Plankilde) IN KpArealformålOmråde,KpArealbrukOmråde
      TEST @Value(Arealstatus) = 1
      TEST @Value(Arealformalkode) != 1110
    TEST_MODE = TEST
    PASSED -> Clipper_5 [CANDIDATE]
    FAILED -> Junction_9
Clipper_5
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator_4
Deaggregator_4
    EXPLODE_INSTANCES = No
    GEOM_NAME_FIELD = _geometry_name
    LIST_ATTR_MODE_LOOKUP = LEAN
    MODE = Flatten All Levels
    SPLIT_COMPOSITES = No
    DEAGGREGATED -> Junction_9
Junction_9
    -> AreaCalculator_5
AreaCalculator_5
    AREA_ATTR = _preBufferArea
    AREA_TYPE = Plane Area
    MULT = 1
    -> Tester_21
Clipper_6
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_6
    OUTSIDE -> Deaggregator_5
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> SpatialRelator [Requestor]
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> SpatialRelator [Supplier]
SpatialRelator
    AGGREGATE_HANDLING = Yes
    CALC_CARD = No
    CURVE_BOUNDARY_RULE_PARAM = Default Rule
    LIST_NAME = _relationships
    PREDICATES = TOUCHES
    SUCCESS_ATTR = _related_suppliers
    -> Tester_15
Tester_15
    BOOL_OP = OR
    TEST_CLAUSE = TEST @Value(_related_suppliers) > 1
    TEST_MODE = TEST
    FAILED -> AreaCalculator_4
AreaCalculator_4
    AREA_ATTR = _area
    AREA_TYPE = Plane Area
    MULT = 1
    -> Tester_22
Tester_22
    BOOL_OP = OR
    TEST_CLAUSE = TEST @Value(_area) < 50
    TEST_MODE = TEST
    PASSED -> Dissolver_2
Dissolver_2
    ACCUM_INPUT_ATTRS = Use Attributes From One Feature
    CLEANING_TOLERANCE = Automatic
    CONNECT_Z_MODE = First Wins
    DEAGGREGATE_INPUT = Yes
    GROUP_BY = Arealformalkode Arealformalsgruppe Arealstatus Ikrafttredelsesdato KpFormal Omradenavn Planid Plankilde Plannavn RpFormal
    AREA -> AreaCalculator
Junction_4
    -> Junction_3
Junction_3
    -> Junction_2
Junction_2
    -> Clipper_2 [CLIPPER]
Junction
    -> Junction_5
Junction_5
    -> Clipper_2 [CANDIDATE]
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_9
Deaggregator_9
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_7
AreaCalculator_7
    AREA_ATTR = _area
    AREA_TYPE = Plane Area
    MULT = 1
    -> Tester_6
Tester_6
    BOOL_OP = OR
    TEST_CLAUSE = TEST @Value(_area) > 250
    TEST_MODE = TEST
    PASSED -> Output (output)
Output (output)

Bookmark: Buffer av bygning og veg
Fkb_tiltak (input)
    -> Bufferer
    -> Bufferer_3
Fkb_bygning (input)
    -> Tester_17
Note: AnnenBygning
Tester_17
    BOOL_OP = OR
    TEST_CLAUSE = TEST objtype != AnnenBygning
    TEST_MODE = TEST
    PASSED -> Bufferer
    PASSED -> Bufferer_3
    FAILED -> Bufferer_9
Note: 30 m buffer
Bufferer_3
    ANGLE = 22.5
    CAP_STYLE = Arc
    CORNER_STYLE = Arc
    MODE = AREA
    OFFSET = 30
    OFFSET_UNITS = NONE
    PRECISION = APPROX
    BUFFERED -> Clipper_5 [CLIPPER]
Note: 10 m buffer
Bufferer
    ANGLE = 22.5
    CAP_STYLE = Arc
    CORNER_STYLE = Arc
    MODE = AREA
    OFFSET = 10
    OFFSET_UNITS = NONE
    PRECISION = APPROX
    BUFFERED -> Clipper [CLIPPER]
Note: 5 m buffer
Bufferer_9
    ANGLE = 22.5
    CAP_STYLE = Arc
    CORNER_STYLE = Arc
    MODE = AREA
    OFFSET = 5
    OFFSET_UNITS = NONE
    PRECISION = APPROX
    BUFFERED -> Clipper_5 [CLIPPER]
    BUFFERED -> Clipper [CLIPPER]
Fkb_veg (input)
    -> Bufferer_2
Note: 5 m buffer
Bufferer_2
    ANGLE = 22.5
    CAP_STYLE = Arc
    CORNER_STYLE = Arc
    MODE = AREA
    OFFSET = 5
    OFFSET_UNITS = NONE
    PRECISION = APPROX
    BUFFERED -> Junction_8

Bookmark: Samferdsel (2010 og 2080)
Note: FKB Veg Buffer
Junction_8
    -> Clipper_4 [CLIPPER]
Clipper_4
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator_2
Deaggregator_2
    EXPLODE_INSTANCES = No
    GEOM_NAME_FIELD = _geometry_name
    LIST_ATTR_MODE_LOOKUP = LEAN
    MODE = Flatten All Levels
    SPLIT_COMPOSITES = No
    DEAGGREGATED -> AreaCalculator_3
AreaCalculator_3
    AREA_ATTR = _area
    AREA_TYPE = Plane Area
    MULT = 1
    -> Tester_9
Tester_9
    BOOL_OP = OR
    TEST_CLAUSE = TEST @Value(_area) > 250
    TEST_MODE = TEST
    PASSED -> Junction_2

Bookmark: Negativ buffer -> positiv buffer
Tester_21
    BOOL_OP = OR
    TEST_CLAUSE = TEST @Value(Plankilde) IN RbFormålOmråde,RpArealformålOmråde
    TEST_MODE = TEST
    PASSED -> Bufferer_4
    PASSED -> Clipper_6 [CANDIDATE]
    FAILED -> Bufferer_6
Bufferer_4
    ANGLE = 22.5
    CAP_STYLE = Arc
    CORNER_STYLE = Arc
    MODE = AREA
    OFFSET = -7.5
    OFFSET_UNITS = NONE
    PRECISION = APPROX
    BUFFERED -> Bufferer_5
Bufferer_5
    ANGLE = 22.5
    CAP_STYLE = Arc
    CORNER_STYLE = Arc
    MODE = AREA
    OFFSET = 7.5
    OFFSET_UNITS = NONE
    PRECISION = APPROX
    BUFFERED -> Clipper_6 [CLIPPER]
    BUFFERED -> Dissolver_2
Bufferer_6
    ANGLE = 22.5
    CAP_STYLE = Arc
    CORNER_STYLE = Arc
    MODE = AREA
    OFFSET = -7.5
    OFFSET_UNITS = NONE
    PRECISION = APPROX
    BUFFERED -> Bufferer_7
Bufferer_7
    ANGLE = 22.5
    CAP_STYLE = Arc
    CORNER_STYLE = Arc
    MODE = AREA
    OFFSET = 7.5
    OFFSET_UNITS = NONE
    PRECISION = APPROX
    BUFFERED -> Deaggregator_8
Deaggregator_8
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator

Bookmark: Siler vekk objekter for bedre ytelse.
AreaCalculator
    AREA_ATTR = _area
    AREA_TYPE = Plane Area
    MULT = 1
    -> Tester_16
Tester_16
    BOOL_OP = OR
    TEST_CLAUSE = TEST @Evaluate(@Value(_preBufferArea)+10) > @Value(_area)
    TEST_MODE = TEST
    PASSED -> LengthCalculator
LengthCalculator
    DIM = 2
    LEN_ATTR = _length
    MULT = 1
    -> AttributeCreator_3
AttributeCreator_3
    ATTR_TABLE = SET_TO _roundness = @Evaluate((@Value(_length)*0.5)/(sqrt(@Value(_area))*2))
    -> Tester_10
Tester_10
    BOOL_OP = COMPOSITE
    COMPOSITE_TEST = 1 AND 2
    TEST_CLAUSE:
      TEST @Value(Arealformalsgruppe) IN 03 Tjenesteyting,04 Handel,06 Næringsvirksomhet,07 Råstoffutvinning,08 Kombinerte formål,
      TEST @Value(_area) < 1000
    TEST_MODE = TEST
    FAILED -> Tester_5
Note: Utelater flater for næring++ under 1 dekar / og under 250 kvm for alle flater
Tester_5
    BOOL_OP = OR
    TEST_CLAUSE = TEST @Value(_area) > 250
    TEST_MODE = TEST
    PASSED -> TestFilter
TestFilter
    DEFAULT_VALUE = Til sirkeltest
    PASSED_TEST_GROUP_OUTPUT = FIRST
    TEST_LIST:
      "BOOL_OP,AND,COMPOSITE_TEST,""""""1 AND 2"""""",TEST_CLAUSE,TEST @Value(_roundness) < 1.25
      TEST @Value(_area) > 1500",>1500,"BOOL_OP,AND,COMPOSITE_TEST,""""""1 AND 2"""""",TEST_CLAUSE,TEST @Value(_roundness) < 1.75
      TEST @Value(_area) > 3000",>3000,"BOOL_OP,AND,COMPOSITE_TEST,""""""1 AND 2"""""",TEST_CLAUSE,TEST @Value(_roundness) < 2
      TEST @Value(_area) > 5000",>5000,"BOOL_OP,OR,COMPOSITE_TEST,""""""1"""""",TEST_CLAUSE,TEST @Value(_area) > 8000",>8000
    >1500 -> Junction_4
    >3000 -> Junction_4
    >5000 -> Junction_4
    >8000 -> Junction_4
    Til sirkeltest -> LargestInnerCircleCreator_2 [Area]

Bookmark: Sirkeltesten
LargestInnerCircleCreator_2
    AccuracyLevel = 20
    Area -> SpatialFilter [Candidate]
    Circles -> Tester_18
Tester_18
    BOOL_OP = COMPOSITE
    COMPOSITE_TEST = 1 OR ( 2 AND 3 AND 4 )
    TEST_CLAUSE:
      TEST @Value(Arealformalsgruppe) IN 03 Tjenesteyting,06 Næringsvirksomhet,07 Råstoffutvinning,08 Kombinerte formål,09 Idrettsanlegg
      TEST @Value(Plankilde) IN KpArealformålOmråde,KpArealbrukOmråde
      TEST @Value(Arealstatus) = 1
      TEST @Value(Arealformalkode) IN 1001,1110,1120
    TEST_MODE = TEST
    PASSED -> Tester_14
    FAILED -> Tester_2
Note: Radius > 15 m
Tester_14
    BOOL_OP = OR
    TEST_CLAUSE = TEST @Value(_radius) > 15
    TEST_MODE = TEST
    PASSED -> Bufferer_8
Note: Radius > 10 m
Tester_2
    BOOL_OP = OR
    TEST_CLAUSE = TEST @Value(_radius) > 10
    TEST_MODE = TEST
    PASSED -> Bufferer_8
Note: Bufrer med -0.1 for å ta høyde for ev. unøyaktighet i sirkelberegning
Bufferer_8
    ANGLE = 22.5
    CAP_STYLE = Arc
    CORNER_STYLE = Arc
    MODE = AREA
    OFFSET = -0.1
    OFFSET_UNITS = NONE
    PRECISION = APPROX
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> Junction_2

FME custom transformer LargestInnerCircleCreator
Creats the largest circle entierly within area/polygon features. The calculation is approximate.

Parameters:
- AccuracyLevel = 30   # High,100%Very Low,10 Select the level of accuracy (will effect performance significantly)

Area (input)
    -> GeometryFilter
GeometryFilter
    BREAK_AGG = No
    GEOM_PORT_NAMES = Area Ellipse
    AREA -> Counter
    ELLIPSE -> Counter
    <UNFILTERED> -> InvalidGeometry (output)
Note: Create an ID for each polygon
Counter
    CNT_ATTR = _count
    DOMAIN = counter
    SCOPE = Global
    START = 0
    -> 2DGridAccumulator
    -> Clipper [CLIPPER]
    -> NeighborFinder [CANDIDATE]
    -> NeighborFinder_2 [CANDIDATE]
    -> Area (output)
Note: Extract Coordinates of circle centepoints
CoordinateExtractor
    LIST_NAME = _indices
    MODE = All Coordinates
    -> 2DEllipseReplacer
Note: Create circles
2DEllipseReplacer
    PRIMAXIS = @Value(_distance)
    ROT = 0
    SECAXIS = @Value(_distance)
    XVALATTR = @Value(_indices{0}.x)
    YVALATTR = @Value(_indices{0}.y)
    ELLIPSE -> AttributeManager
Note: CleanUp
AttributeManager
    ATTR_TABLE:
      REMOVE _count
      REMOVE _column
      REMOVE _row
      RENAME_SET_VALUE _distance > _radius
      REMOVE _angle
      REMOVE _candidate_angle
      REMOVE _candidate_label_angle
      REMOVE _closest_candidate_x
      REMOVE _closest_candidate_y
      REMOVE _closest_base_x
      REMOVE _closest_base_y
      REMOVE _indices{}.z
      SET_TO _centre_x = @Value(_indices{0}.x)
      SET_TO _centre_y = @Value(_indices{0}.y)
    -> AttributeRemover
AttributeRemover
    LIST_ATTRS = _indices{}.x _indices{}.y
    -> Circles (output)
Circles (output)
Area (output)
InvalidGeometry (output)

Bookmark: Break Polygon into parts (1)
Note: Create Grid over each polygon
2DGridAccumulator
    COL_ATTR = _column
    GRID_TYPE = Polygons
    GROUP_BY = _count
    ROW_ATTR = _row
    SIZE_TYPE = Number of Cells
    STARTINGCORNER = Lower Left
    XCOUNT = $(AccuracyLevel)
    YCOUNT = $(AccuracyLevel)
    GRID -> Clipper [CLIPPEE]
Note: Clip Grid so that only features in each polygon remain
Clipper
    BOUNDARY_CASES = Treat as Inside
    CLIPPED_ATTR = _clipped
    CLIP_TYPE = Multiple Clippers
    CONNECT_Z_MODE = First Wins
    CREATE_AGGREGATES = Yes
    GROUP_BY = _count
    LINES_AS_SEGMENTS = No
    PRESERVE_CLIPPEE_EXTENTS = No
    INSIDE -> NeighborFinder [BASE]

Bookmark: Find Centre Grid Unit (2)
NeighborFinder
    ATTR_ACCUM_MODE = Merge Candidate
    ATTR_CONFLICT_RES = Use Base
    CANDIDATES_FIRST = No
    GROUP_BY = _count
    INSERT_VERTEX = No
    K = 1
    MODE = Bases and Candidates
    TREAT_POLYGON_AS = Lines
    MATCHED -> Sorter
Sorter
    SORT_PARM = _count NUMERIC ASCENDING _distance NUMERIC DESCENDING
    SORTED -> Sampler
Sampler
    GROUP_BY = _count
    RATE = 1
    SAMPLE_MODE = No
    SAMPLE_TYPE_LONG = First N Features
    SAMPLED -> 2DGridAccumulator_2

Bookmark: Repeat Stepts 2 and 3 to increase accuracy
2DGridAccumulator_2
    COL_ATTR = _column
    GRID_TYPE = Points (Centers)
    GROUP_BY = _count
    ROW_ATTR = _row
    SIZE_TYPE = Number of Cells
    STARTINGCORNER = Lower Left
    XCOUNT = 25
    YCOUNT = 25
    GRID -> NeighborFinder_2 [BASE]
NeighborFinder_2
    ATTR_ACCUM_MODE = Merge Candidate
    ATTR_CONFLICT_RES = Use Base
    CANDIDATES_FIRST = No
    GROUP_BY = _count
    INSERT_VERTEX = No
    K = 1
    MODE = Bases and Candidates
    TREAT_POLYGON_AS = Lines
    MATCHED -> Sorter_2
Sorter_2
    SORT_PARM = _count NUMERIC ASCENDING _distance NUMERIC DESCENDING
    SORTED -> Sampler_2
Sampler_2
    GROUP_BY = _count
    RATE = 1
    SAMPLE_MODE = No
    SAMPLE_TYPE_LONG = First N Features
    SAMPLED -> CoordinateExtractor
